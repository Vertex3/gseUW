FME workspace BuildingConnectors.fmw

Parameters:
- DestDataset_GEODATABASE_SDE = campus   # Destination Esri ArcSDE Geodatabase Dataset
- SourceDataset_GEODATABASE_SDE = campus   # Source Esri ArcSDE Geodatabase Dataset

Readers:
- GEODATABASE_SDE_2: GEODATABASE_SDE from $(SourceDataset_GEODATABASE_SDE)

Writers:
- GEODATABASE_SDE_1: GEODATABASE_SDE to $(DestDataset_GEODATABASE_SDE)

AttributeCreator_4
    NUM_PRIOR_FEATURES = 0
    NUM_SUBSEQUENT_FEATURES = 0
    ATTR_LIST = pt_type,dr
    -> PointOnPointOverlayer_2
AttributeCreator_2
    NUM_PRIOR_FEATURES = 0
    NUM_SUBSEQUENT_FEATURES = 0
    ATTR_LIST = pt_type,ext
    -> PointOnLineOverlayer [input 2]
    -> NeighborFinder_3 [input 2]
Intersector_2
    DUPLICATE_Z_NODES = No
    SEPARATE_COLLINEAR_SEGMENTS = No
    PERFORM_SELF_INTERSECTION = No
    SEG_ATTR = _segments
    OV_ATTR = _overlaps
    NODE -> Intersector_2_Node
Intersector_2_Node: Inspector
Intersector_4
    DUPLICATE_Z_NODES = No
    SEPARATE_COLLINEAR_SEGMENTS = No
    PERFORM_SELF_INTERSECTION = No
    SEG_ATTR = _segments
    OV_ATTR = _overlaps
    NODE -> Intersector_3_Node_2
Intersector_3_Node_2: Inspector
Intersector_3
    DUPLICATE_Z_NODES = No
    SEPARATE_COLLINEAR_SEGMENTS = No
    PERFORM_SELF_INTERSECTION = No
    SEG_ATTR = _segments
    OV_ATTR = _overlaps
    NODE -> Intersector_3_Node
Intersector_3_Node: Inspector
CoordinateExtractor_5
    Y_ATTR = _y
    X_ATTR = _x
    Z_DEFAULT = -9999
    Z_ATTR = _z
    IND = 0
    -> PointOnPointOverlayer
Intersector
    DUPLICATE_Z_NODES = No
    SEPARATE_COLLINEAR_SEGMENTS = No
    PERFORM_SELF_INTERSECTION = No
    SEG_ATTR = _segments
    OV_ATTR = _overlaps
    NODE -> Intersector_Node
Intersector_Node: Inspector

Bookmark: exterior doors
DBO.RT_DoorPoint (reader GEODATABASE_SDE_2)
    attributes: geodb_oid integer, OBJECTID integer, SITEID char(60), BUILDINGID char(60), FLOORCODE char(60), FLOORID char(60), DOOR char(20), DOORID char(33), SPACEID1 char(50), SPACEID2 char(50), ADA smallint, FITNESS smallint, ACTIVE smallint, ISPUBLIC smallint, WIDTH double, HEIGHT double, NAME char(255), EMERGENCY char(255), DELAY double, SUNTIMEWINDOWSTART date, SUNTIMEWINDOWEND date, MONTIMEWINDOWSTART date, MONTIMEWINDOWEND date, TUESTIMEWINDOWSTART date, TUESTIMEWINDOWEND date, WEDTIMEWINDOWSTART date, WEDTIMEWINDOWEND date, THURSTIMEWINDOWSTART date, THURSTIMEWINDOWEND date, FRITIMEWINDOWSTART date,
      FRITIMEWINDOWEND date, SATTIMEWINDOWSTART date, SATTIMEWINDOWEND date, SOURCEID char(30), SOURCEDWG char(60), LASTUPDATE date, LASTEDITOR char(30)
    -> Tester
    -> AttributeCreator_4
    -> Intersector_2
Tester
    TEST_MODE = Automatic
    TEST_DESCRIPTION = ""
    BOOL_OP = OR
    TEST_CLAUSE:
      TEST SPACEID2 ATTRIBUTE_IS_EMPTY <Unused>
      TEST SPACEID1 ATTRIBUTE_IS_EMPTY <Unused>
    PASSED -> AttributeCreator
AttributeCreator
    NUM_PRIOR_FEATURES = 0
    NUM_SUBSEQUENT_FEATURES = 0
    ATTR_LIST = pt_type,door
    -> CoordinateExtractor_2
CoordinateExtractor_2
    Y_ATTR = _y
    X_ATTR = _x
    Z_DEFAULT = -9999
    Z_ATTR = _z
    IND = 0
    -> PointOnPointOverlayer
PointOnPointOverlayer
    GRP_BY = _z
    TOLERANCE = .01
    OV_ATTR = _overlaps
    POINT -> Tester_2
Tester_2
    TEST_MODE = Automatic
    TEST_DESCRIPTION = ""
    BOOL_OP = AND
    TEST_CLAUSE:
      TEST @Value(_overlaps) = 1
      TEST @Value(pt_type) = door
    PASSED -> NeighborFinder_2 [input 1]

Bookmark: room points
DBO.RT_RoomPoint (reader GEODATABASE_SDE_2)
    attributes: geodb_oid integer, OBJECTID integer, SITEID char(60), BUILDINGID char(60), FLOORCODE char(60), FLOORID char(60), ROOMNUMBER char(26), SPACEID char(25), ADA smallint, FITNESS smallint, ACTIVE smallint, ISPUBLIC smallint, NAME char(255), EMERGENCY char(255), SOURCEID char(30), SOURCEDWG char(60), LASTUPDATE date, LASTEDITOR char(30)
    -> Chopper_2
    -> AttributeCreator_3
AttributeCreator_3
    NUM_PRIOR_FEATURES = 0
    NUM_SUBSEQUENT_FEATURES = 0
    ATTR_LIST = pt_type,rm
    -> PointOnPointOverlayer_2

Bookmark: interior lines
DBO.RT_LineTransition (reader GEODATABASE_SDE_2)
    attributes: geodb_oid integer, OBJECTID integer, SITEID char(60), BUILDINGID char(60), FLOORCODE char(60), FLOORID char(60), SPACEID char(50), ADA smallint, EVAC char(255), FITNESS smallint, ACTIVE smallint, ISPUBLIC smallint, SURFACE char(255), SPEED double, NAME char(255), WIDTH double, HEIGHT double, ONEWAY char(255), EMERGENCY char(255), FROMFLOOR char(255), TOFLOOR char(255), ROUTECLASS smallint, SOURCEID char(30), SOURCEDWG char(60), LASTUPDATE date, LASTEDITOR char(30), SHAPE.STLength() double
    -> Chopper_3
    -> Chopper_2
    -> PointOnLineOverlayer [input 2]
    -> Intersector_4
DBO.RT_LineRmConnector (reader GEODATABASE_SDE_2)
    attributes: geodb_oid integer, OBJECTID integer, SITEID char(60), BUILDINGID char(60), FLOORCODE char(60), FLOORID char(60), ROOMNUMBER char(26), SPACEID char(25), ADA smallint, FITNESS smallint, ACTIVE smallint, ISPUBLIC smallint, SURFACE char(255), SPEED double, WIDTH double, HEIGHT double, NAME char(255), ONEWAY char(255), EMERGENCY char(255), FROMFLOOR char(255), TOFLOOR char(255), ROUTECLASS smallint, SOURCEID char(30), SOURCEDWG char(60), LASTUPDATE date, LASTEDITOR char(30), SHAPE.STLength() double
    -> Chopper_3
    -> Chopper_2
    -> PointOnLineOverlayer [input 2]
DBO.RT_LineInterior (reader GEODATABASE_SDE_2)
    attributes: geodb_oid integer, OBJECTID integer, SITEID char(60), BUILDINGID char(60), FLOORCODE char(60), FLOORID char(60), SpaceID char(50), ADA smallint, EVAC char(255), FITNESS smallint, ACTIVE smallint, ISPUBLIC smallint, SURFACE char(255), SPEED double, NAME char(255), WIDTH double, HEIGHT double, ONEWAY char(255), EMERGENCY char(255), FROMFLOOR char(255), TOFLOOR char(255), ROUTECLASS smallint, SOURCEID char(30), SOURCEDWG char(60), LASTUPDATE date, LASTEDITOR char(30), SHAPE.STLength() double
    -> Chopper_3
    -> PointOnLineOverlayer [input 2]
    -> Chopper_2
    -> Intersector_3
Chopper_3
    CHOPPED_ATTR = _chopped
    MAX_VERTICES = 1
    MODE = By Vertex
    REMNANT_ATTR = _remnant
    -> CoordinateExtractor_5

Bookmark: Exterior dead ends
DBO.RT_LineExterior (reader GEODATABASE_SDE_2)
    attributes: geodb_oid integer, OBJECTID integer, ADA smallint, FITNESS smallint, ACTIVE smallint, SURFACE char(255), SPEED double, NAME char(255), WIDTH double, HEIGHT double, ISPUBLIC smallint, ONEWAY char(255), EMERGENCY char(255), FROMFLOOR char(255), TOFLOOR char(255), ROUTECLASS smallint, SOURCEID char(30), SOURCEDWG char(60), LASTUPDATE date, LASTEDITOR char(30), SHAPE.STLength() double
    -> Chopper
    -> Chopper_2
    -> Intersector
    -> Intersector_2
    -> Intersector_3
    -> Intersector_4
Chopper
    CHOPPED_ATTR = _chopped
    MAX_VERTICES = 1
    MODE = By Vertex
    REMNANT_ATTR = _remnant
    -> CoordinateExtractor_3
CoordinateExtractor_3
    Y_ATTR = _y
    X_ATTR = _x
    Z_DEFAULT = -9999
    Z_ATTR = _z
    IND = 0
    -> PointOnPointOverlayer_3
    -> PointOnPointOverlayer
PointOnPointOverlayer_3
    GRP_BY = _z
    TOLERANCE = .01
    OV_ATTR = _overlaps
    POINT -> Tester_4
Tester_4
    TEST_MODE = Automatic
    TEST_DESCRIPTION = ""
    BOOL_OP = OR
    TEST_CLAUSE = TEST @Value(_overlaps) = 0
    PASSED -> NeighborFinder_2 [input 2]
    PASSED -> AttributeCreator_2

Bookmark: temporary fix
NeighborFinder_2
    INSERT_VERTEX = No
    TREAT_POLYGON_AS = Lines
    MAX = 10
    CLOSE_LIST_NAME = _close
    CANDIDATES_FIRST = No
    MATCHED -> ListSorter_2
    UNMATCHED_BASE -> AttributeCreator_8
ListSorter_2
    TYPE = Numeric
    SRC_LIST = _close{}.distance
    ORDER = Increasing
    -> 3DPointAdder_2
3DPointAdder_2
    XVALATTR = @Value(_close{0}._x)
    ZVALATTR = @Value(_close{0}._z)
    YVALATTR = @Value(_close{0}._y)
    -> GeometryFilter
GeometryFilter
    BREAK_AGG = No
    LINE -> AttributeCreator_6
AttributeCreator_6
    NUM_PRIOR_FEATURES = 0
    NUM_SUBSEQUENT_FEATURES = 0
    ATTR_LIST = ConnectionType,ExteriorDoor
    -> GeometryValidator
AttributeCreator_8
    NUM_PRIOR_FEATURES = 0
    NUM_SUBSEQUENT_FEATURES = 0
    ATTR_LIST = ErrorType,ExteriorDoor
    -> GeometryValidator_2
GeometryValidator_2
    SHELL_VALIDATION = SHELL_VALIDATION
    CHECK_HOLE_TOUCHING_POLYGON = No
    DUP_COORDS_CHECK_Z = Yes
    NULL_REMOVAL = NULL_REMOVAL
    TYPE_REPAIR = TYPE_REPAIR
    SELF_INTERSECTING = SELF_INTERSECTING
    PRESETS = Custom
    ARC_ENDPOINT_TOLERANCE_MODE = Auto
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%""%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    PLANAR_SURFACE = PLANAR_SURFACE
    REPAIR = Yes
    ISSUE_ATTR_NAME = _issues
    MISSING_TEXTURE_COORDINATES = MISSING_TEXTURE_COORDINATES
    SOLID_VOID_REPAIR = SOLID_VOID_REPAIR
    OGC_SIMPLE_CHECK = OGC_SIMPLE_CHECK
    PLANAR_TOLERANCE_MODE = Auto
    NAN_REMOVAL = NAN_REMOVAL
    MISSING_VERTEX_NORMALS = MISSING_VERTEX_NORMALS
    OGC_VALID_CHECK = OGC_VALID_CHECK
    CONSECUTIVE_IDENTICAL_VERTICES_2D = CONSECUTIVE_IDENTICAL_VERTICES_2D
    PASSED -> RT_Errors (writer GEODATABASE_SDE_1)
    REPAIRED -> RT_Errors (writer GEODATABASE_SDE_1)
RT_Errors (writer GEODATABASE_SDE_1) [off]
    attributes: SITEID char(60), BUILDINGID char(60), FLOORCODE char(60), FLOORID char(60), DOOR char(20), DOORID char(33), SPACEID1 char(50), SPACEID2 char(50), SOURCEID char(30), SOURCEDWG char(60), LASTUPDATE date, LASTEDITOR char(30), ErrorType char(30)
GeometryValidator
    SHELL_VALIDATION = SHELL_VALIDATION
    CHECK_HOLE_TOUCHING_POLYGON = No
    DUP_COORDS_CHECK_Z = Yes
    NULL_REMOVAL = NULL_REMOVAL
    TYPE_REPAIR = TYPE_REPAIR
    SELF_INTERSECTING = SELF_INTERSECTING
    PRESETS = Custom
    ARC_ENDPOINT_TOLERANCE_MODE = Auto
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%""%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    PLANAR_SURFACE = PLANAR_SURFACE
    REPAIR = Yes
    ISSUE_ATTR_NAME = _issues
    MISSING_TEXTURE_COORDINATES = MISSING_TEXTURE_COORDINATES
    SOLID_VOID_REPAIR = SOLID_VOID_REPAIR
    OGC_SIMPLE_CHECK = OGC_SIMPLE_CHECK
    PLANAR_TOLERANCE_MODE = Auto
    NAN_REMOVAL = NAN_REMOVAL
    MISSING_VERTEX_NORMALS = MISSING_VERTEX_NORMALS
    OGC_VALID_CHECK = OGC_VALID_CHECK
    CONSECUTIVE_IDENTICAL_VERTICES_2D = CONSECUTIVE_IDENTICAL_VERTICES_2D
    PASSED -> DBO.RT_BuildingConnector (writer GEODATABASE_SDE_1)
    REPAIRED -> DBO.RT_BuildingConnector (writer GEODATABASE_SDE_1)
    PASSED -> Intersector
    REPAIRED -> Intersector
DBO.RT_BuildingConnector (writer GEODATABASE_SDE_1) [off]
    attributes: ADA integer, FITNESS integer, ACTIVE integer, SURFACE char(254), SPEED double, NAME char(254), WIDTH double, HEIGHT double, ISPUBLIC integer, ONEWAY char(254), EMERGENCY char(254), FROMFLOOR char(254), TOFLOOR char(254), ROUTECLASS integer, ConnectionType char(30)

Bookmark: inerior line dead ends
Chopper_2
    CHOPPED_ATTR = _chopped
    MAX_VERTICES = 1
    MODE = By Vertex
    REMNANT_ATTR = _remnant
    -> CoordinateExtractor_6
CoordinateExtractor_6
    Y_ATTR = _y
    X_ATTR = _x
    Z_DEFAULT = -9999
    Z_ATTR = _z
    IND = 0
    -> PointOnLineOverlayer [input 1]
PointOnLineOverlayer
    TOLERANCE = .01
    OV_ATTR = _overlaps
    POINT -> Tester_6
Tester_6
    TEST_MODE = Automatic
    TEST_DESCRIPTION = ""
    BOOL_OP = AND
    TEST_CLAUSE:
      TEST @Value(_overlaps) = 1
      TEST @Value(pt_type) != ext
    PASSED -> PointOnPointOverlayer_2
PointOnPointOverlayer_2
    TOLERANCE = .01
    OV_ATTR = _overlaps2
    POINT -> Tester_7
Tester_7
    TEST_MODE = Automatic
    TEST_DESCRIPTION = ""
    BOOL_OP = AND
    TEST_CLAUSE:
      TEST @Value(_overlaps2) = 0
      TEST @Value(pt_type) != rm
      TEST @Value(pt_type) != dr
    PASSED -> NeighborFinder_3 [input 1]

Bookmark: int dead end connector to ext
NeighborFinder_3
    INSERT_VERTEX = No
    TREAT_POLYGON_AS = Lines
    MAX = 5
    CLOSE_LIST_NAME = _close
    CANDIDATES_FIRST = No
    MATCHED -> ListSorter_3
    UNMATCHED_BASE -> AttributeCreator_7
AttributeCreator_7
    NUM_PRIOR_FEATURES = 0
    NUM_SUBSEQUENT_FEATURES = 0
    ATTR_LIST = ErrorType,InteriorLine
    -> GeometryValidator_2
ListSorter_3
    TYPE = Numeric
    SRC_LIST = _close{}.distance
    ORDER = Increasing
    -> 3DPointAdder_3
3DPointAdder_3
    XVALATTR = @Value(_close{0}._x)
    ZVALATTR = @Value(_close{0}._z)
    YVALATTR = @Value(_close{0}._y)
    -> AttributeCreator_5
AttributeCreator_5
    NUM_PRIOR_FEATURES = 0
    NUM_SUBSEQUENT_FEATURES = 0
    ATTR_LIST = ConnectionType,InteriorLine
    -> GeometryValidator
