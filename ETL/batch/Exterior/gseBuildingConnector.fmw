FME workspace gseBuildingConnector.fmw

Parameters:
- SourceDataset_GEODATABASE_SDE = sde   # Source Esri ArcSDE Geodatabase Dataset
- DestDataset_GEODATABASE_SDE = sde   # Destination Esri ArcSDE Geodatabase Dataset
- Snap_Distance = 4   # Distance to snap line endpoints

Readers:
- GEODATABASE_SDE_1: GEODATABASE_SDE from $(SourceDataset_GEODATABASE_SDE)

Writers:
- GEODATABASE_SDE_2: GEODATABASE_SDE to $(DestDataset_GEODATABASE_SDE)

DBO.RT_LineExterior (reader GEODATABASE_SDE_1)
    attributes: geodb_oid integer, OBJECTID integer, ADA smallint, FITNESS smallint, ACTIVE smallint, SURFACE char(255), SPEED double, NAME char(255), WIDTH double, HEIGHT double, ISPUBLIC smallint, ONEWAY char(255), EMERGENCY char(255), FROMFLOOR char(255), TOFLOOR char(255), ROUTECLASS smallint, SOURCEID char(30), SOURCEDWG char(60), LASTUPDATE date, LASTEDITOR char(30), SHAPE.STLength() double
    -> GeometryExtractor
GeometryExtractor
    KIND_LONG = FME Binary
    ATTR = geometry
    -> CoordinateExtractor_3
    -> SpatialRelator_3 [Supplier]
    -> CoordinateCounter_2
CoordinateExtractor_3
    Y_ATTR = _y
    IND = 0
    Z_DEFAULT = -9999
    Z_ATTR = _z
    X_ATTR = _x
    -> VertexCreator_3
VertexCreator_3
    MODE_NAME = Replace with Point
    ZVAL = @Value(_z)
    XVAL = @Value(_x)
    YVAL = @Value(_y)
    -> SpatialRelator_3 [Requestor]
CoordinateCounter_2
    CNT_ATTR = _coordcount
    -> CoordinateExtractor_4
CoordinateExtractor_4
    Y_ATTR = _y
    IND = @Value(_coordcount) - 1
    Z_DEFAULT = -9999
    Z_ATTR = _z
    X_ATTR = _x
    -> VertexCreator_6
VertexCreator_6
    MODE_NAME = Replace with Point
    ZVAL = @Value(_z)
    XVAL = @Value(_x)
    YVAL = @Value(_y)
    -> SpatialRelator_3 [Requestor]
DBO.RT_LineRmConnector (reader GEODATABASE_SDE_1)
    attributes: geodb_oid integer, OBJECTID integer, SITEID char(60), BUILDINGID char(60), FLOORCODE char(60), FLOORID char(60), ROOMNUMBER char(26), SPACEID char(25), ADA smallint, FITNESS smallint, ACTIVE smallint, ISPUBLIC smallint, SURFACE char(255), SPEED double, WIDTH double, HEIGHT double, NAME char(255), ONEWAY char(255), EMERGENCY char(255), FROMFLOOR char(255), TOFLOOR char(255), ROUTECLASS smallint, SOURCEID char(30), SOURCEDWG char(60), LASTUPDATE date, LASTEDITOR char(30), SHAPE.STLength() double
    -> SpatialRelator [Requestor]
DBO.RT_LineInterior (reader GEODATABASE_SDE_1)
    attributes: geodb_oid integer, OBJECTID integer, SITEID char(60), BUILDINGID char(60), FLOORCODE char(60), FLOORID char(60), SpaceID char(50), ADA smallint, EVAC char(255), FITNESS smallint, ACTIVE smallint, ISPUBLIC smallint, SURFACE char(255), SPEED double, NAME char(255), WIDTH double, HEIGHT double, ONEWAY char(255), EMERGENCY char(255), FROMFLOOR char(255), TOFLOOR char(255), ROUTECLASS smallint, SOURCEID char(30), SOURCEDWG char(60), LASTUPDATE date, LASTEDITOR char(30), SHAPE.STLength() double
    -> SpatialRelator [Requestor]
DBO.RT_LineTransition (reader GEODATABASE_SDE_1)
    attributes: geodb_oid integer, OBJECTID integer, SITEID char(60), BUILDINGID char(60), FLOORCODE char(60), FLOORID char(60), SPACEID char(50), ADA smallint, EVAC char(255), FITNESS smallint, ACTIVE smallint, ISPUBLIC smallint, SURFACE char(255), SPEED double, NAME char(255), WIDTH double, HEIGHT double, ONEWAY char(255), EMERGENCY char(255), FROMFLOOR char(255), TOFLOOR char(255), ROUTECLASS smallint, SOURCEID char(30), SOURCEDWG char(60), LASTUPDATE date, LASTEDITOR char(30), SHAPE.STLength() double
    -> SpatialRelator [Requestor]
DBO.RT_RoomPoint (reader GEODATABASE_SDE_1)
    attributes: geodb_oid integer, OBJECTID integer, SITEID char(60), BUILDINGID char(60), FLOORCODE char(60), FLOORID char(60), ROOMNUMBER char(26), SPACEID char(25), ADA smallint, FITNESS smallint, ACTIVE smallint, ISPUBLIC smallint, NAME char(255), EMERGENCY char(255), SOURCEID char(30), SOURCEDWG char(60), LASTUPDATE date, LASTEDITOR char(30)
    -> SpatialRelator [Supplier]
SpatialRelator
    LIST_NAME = _relationships
    CURVE_BOUNDARY_RULE_PARAM = Default Rule
    CALC_CARD = Yes
    SUCCESS_ATTR = _related_candidates
    PREDICATES = TOUCHES
    -> ListElementCounter
ListElementCounter
    LIST_NAME = _relationships{}
    CNT_ATTR = _element_count
    -> TestFilter
TestFilter
    TEST_LIST = BOOL_OP,OR,COMPOSITE_TEST,<Unused>,TEST_CLAUSE,"TEST @Value(_element_count) = 0",no rooms
    DEFAULT_VALUE = <UNFILTERED>
    no rooms -> SpatialRelator_2 [Requestor]
    no rooms -> SpatialRelator_3 [Supplier]
    no rooms -> CoordinateExtractor_2
CoordinateExtractor_2
    Y_ATTR = _yline0
    IND = 0
    Z_DEFAULT = 0
    Z_ATTR = _zline0
    X_ATTR = _xline0
    -> CoordinateCounter_3
CoordinateCounter_3
    CNT_ATTR = _coordcount
    -> CoordinateExtractor_6
CoordinateExtractor_6
    Y_ATTR = _ylinen
    IND = @Value(_coordcount) - 1
    Z_DEFAULT = 0
    Z_ATTR = _zlinen
    X_ATTR = _xlinen
    -> NeighborFinder [CANDIDATE]
SpatialRelator_3
    LIST_NAME = _relationships
    CURVE_BOUNDARY_RULE_PARAM = Default Rule
    CALC_CARD = No
    SUCCESS_ATTR = _related_candidates
    PREDICATES = TOUCHES
    -> ListElementCounter_3
ListElementCounter_3
    LIST_NAME = _relationships{}
    CNT_ATTR = _element_count
    -> TestFilter_4
TestFilter_4
    TEST_LIST = BOOL_OP,OR,COMPOSITE_TEST,<Unused>,TEST_CLAUSE,"TEST @Value(_element_count) = 1",Dangling lines
    DEFAULT_VALUE = <UNFILTERED>
    Dangling lines -> BulkAttributeRemover_2
BulkAttributeRemover_2
    ATTR_EXP = _rel*
    -> NeighborFinder [BASE]
    -> NeighborFinder_2 [BASE]
NeighborFinder
    TREAT_POLYGON_AS = Lines
    MAX = $(Snap_Distance)
    CLOSE_LIST_NAME = _close
    CANDIDATES_FIRST = No
    INSERT_VERTEX = No
    MATCHED -> AttributeCreator_5
AttributeCreator_5
    ATTR_LIST = ConnectionType,InteriorLine
    -> CreateLineFromPts [AnchoredSnapper_Anchor]
    -> CreateLineFromPts [VertexCreator_4_Input]
CreateLineFromPts
    Tester_Passed -> DBO.RT_BuildingConnector (writer GEODATABASE_SDE_2)
DBO.RT_BuildingConnector (writer GEODATABASE_SDE_2)
    attributes: geodb_oid integer, OBJECTID integer, ADA integer, FITNESS integer, ACTIVE integer, SURFACE char(254), SPEED double, NAME char(254), WIDTH double, HEIGHT double, ISPUBLIC integer, ONEWAY char(254), EMERGENCY char(254), FROMFLOOR char(254), TOFLOOR char(254), ROUTECLASS integer, ConnectionType char(30), SHAPE.STLength() double
DBO.RT_Errors (writer GEODATABASE_SDE_2) [off]
    attributes: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

Bookmark: Has Exterior Door
DBO.RT_DoorPoint (reader GEODATABASE_SDE_1)
    attributes: geodb_oid integer, OBJECTID integer, SITEID char(60), BUILDINGID char(60), FLOORCODE char(60), FLOORID char(60), DOOR char(20), DOORID char(33), SPACEID1 char(50), SPACEID2 char(50), ADA smallint, FITNESS smallint, ACTIVE smallint, ISPUBLIC smallint, WIDTH double, HEIGHT double, NAME char(255), EMERGENCY char(255), DELAY double, SUNTIMEWINDOWSTART date, SUNTIMEWINDOWEND date, MONTIMEWINDOWSTART date, MONTIMEWINDOWEND date, TUESTIMEWINDOWSTART date, TUESTIMEWINDOWEND date, WEDTIMEWINDOWSTART date, WEDTIMEWINDOWEND date, THURSTIMEWINDOWSTART date, THURSTIMEWINDOWEND date, FRITIMEWINDOWSTART date,
      FRITIMEWINDOWEND date, SATTIMEWINDOWSTART date, SATTIMEWINDOWEND date, SOURCEID char(30), SOURCEDWG char(60), LASTUPDATE date, LASTEDITOR char(30)
    -> CoordinateExtractor
CoordinateExtractor
    Y_ATTR = _ydoor
    IND = 0
    Z_DEFAULT = 0
    Z_ATTR = _zdoor
    X_ATTR = _xdoor
    -> TestFilter_2
TestFilter_2
    TEST_LIST:
      BOOL_OP,OR,COMPOSITE_TEST,<Unused>,TEST_CLAUSE,"TEST SPACEID1 ATTRIBUTE_VALUE_NULL """"
      TEST SPACEID1 ATTRIBUTE_IS_EMPTY """"
      TEST SPACEID1 ATTRIBUTE_IS_MISSING """"
      TEST @Value(SPACEID1) =  ",No SPACEID1,BOOL_OP,OR,COMPOSITE_TEST,<Unused>,TEST_CLAUSE,"TEST SPACEID2 ATTRIBUTE_VALUE_NULL """"
      TEST SPACEID2 ATTRIBUTE_IS_EMPTY """"
      TEST SPACEID2 ATTRIBUTE_IS_MISSING """"
      TEST @Value(SPACEID2) =  ",No SPACEID2
    DEFAULT_VALUE = <UNFILTERED>
    No SPACEID1 -> SpatialRelator_2 [Supplier]
    No SPACEID2 -> SpatialRelator_2 [Supplier]
SpatialRelator_2
    LIST_NAME = _relationships
    CURVE_BOUNDARY_RULE_PARAM = Default Rule
    CALC_CARD = Yes
    SUCCESS_ATTR = _related_candidates
    PREDICATES = TOUCHES
    -> ListElementCounter_2
ListElementCounter_2
    LIST_NAME = _relationships{}
    CNT_ATTR = _element_count
    -> TestFilter_3
TestFilter_3
    TEST_LIST = BOOL_OP,OR,COMPOSITE_TEST,<Unused>,TEST_CLAUSE,"TEST @Value(_element_count) = 1",Ext Door
    DEFAULT_VALUE = <UNFILTERED>
    Ext Door -> BulkAttributeRemover
BulkAttributeRemover
    ATTR_EXP = _rel*
    -> NeighborFinder_2 [CANDIDATE]
NeighborFinder_2
    TREAT_POLYGON_AS = Lines
    MAX = $(Snap_Distance)
    CLOSE_LIST_NAME = _close
    CANDIDATES_FIRST = No
    INSERT_VERTEX = No
    MATCHED -> AttributeCreator_6
    UNMATCHED_BASE -> AttributeCreator
AttributeCreator_6
    ATTR_LIST = ConnectionType,ExteriorDoor
    NUM_PRIOR_FEATURES = 0
    NUM_SUBSEQUENT_FEATURES = 0
    -> CreateLineFromPts [AnchoredSnapper_Anchor]
    -> CreateLineFromPts [VertexCreator_4_Input]
AttributeCreator
    ATTR_LIST = ErrorType,No room and no door
    -> VertexCreator_2
VertexCreator_2
    MODE_NAME = Replace with Point
    ZVAL = @Value(_z)
    XVAL = @Value(_x)
    YVAL = @Value(_y)

FME custom transformer CreateLineFromPts

VertexCreator_4_Input (input)
    -> AttributeExposer
AttributeExposer
    ATTR_LIST = _x,_y,_z,_close{0}._xline0,_close{0}._yline0,_close{0}._zline0,_close{0}._xlinen,_close{0}._ylinen,_close{0}._zlinen,geodb_oid,ConnectionType,_xdoor,_ydoor,_zdoor,_closest_candidate_y,_closest_candidate_x
    -> TestFilter
TestFilter
    TEST_LIST = BOOL_OP,OR,COMPOSITE_TEST,<Unused>,TEST_CLAUSE,"TEST @Value(ConnectionType) = ExteriorDoor",door
    DEFAULT_VALUE = <UNFILTERED>
    door -> VertexCreator_6
    <UNFILTERED> -> VertexCreator_4
VertexCreator_4
    MODE_NAME = Replace with Point
    ZVAL = @Value(_z)
    XVAL = @Value(_x)
    YVAL = @Value(_y)
    -> VertexCreator_5
    -> VertexCreator_2
VertexCreator_2
    MODE_NAME = Add Point
    ZVAL = @Value(_close{0}._zline0)
    XVAL = @Value(_close{0}._xline0)
    YVAL = @Value(_close{0}._yline0)
    -> GeometryExtractor
GeometryExtractor
    KIND_LONG = FME Binary
    ATTR = g0
    -> LengthCalculator_3
LengthCalculator_3
    DIM = 3
    MULT = 1
    LEN_ATTR = _length0
    -> FeatureMerger [REQUESTOR]
VertexCreator_5
    MODE_NAME = Add Point
    ZVAL = @Value(_close{0}._zlinen)
    XVAL = @Value(_close{0}._xlinen)
    YVAL = @Value(_close{0}._ylinen)
    -> GeometryExtractor_3
GeometryExtractor_3
    KIND_LONG = FME Binary
    ATTR = gn
    -> LengthCalculator_4
LengthCalculator_4
    DIM = 3
    MULT = 1
    LEN_ATTR = _lengthn
    -> FeatureMerger [SUPPLIER]
FeatureMerger
    PROCESS_DUPS = No
    SUPPLIERS_FIRST = No
    SUPPLIER_PREFIX_DUMMY = YES
    MERGE_TYPE = Attributes Only
    JOIN_KEYS = @Value(geodb_oid) @Value(geodb_oid) AUTO
    IGNORE_NULLS = Yes
    MERGED -> longer
longer: Tester
    TEST_CLAUSE = NUM_TEST @Value(_length0) > @Value(_lengthn)
    BOOL_OP = OR
    TEST_MODE = Automatic
    TEST_DESCRIPTION = ""
    PASSED -> GeometryReplacer
    FAILED -> GeometryReplacer_2
GeometryReplacer
    KIND_LONG = FME Binary
    REMOVE_ATTRIBUTE = No
    SOURCE = @Value(gn)
    -> AnchoredSnapper [CANDIDATE]
GeometryReplacer_2
    KIND_LONG = FME Binary
    REMOVE_ATTRIBUTE = No
    SOURCE = @Value(g0)
    -> AnchoredSnapper [CANDIDATE]
VertexCreator_6 [off]
    MODE_NAME = Replace with Point
    ZVAL = @Value(_zdoor)
    XVAL = @Value(_closest_candidate_x)
    YVAL = @Value(_closest_candidate_y)
    -> VertexCreator_3
VertexCreator_3
    MODE_NAME = Add Point
    ZVAL = @Value(_zdoor)
    XVAL = @Value(_xdoor)
    YVAL = @Value(_ydoor)
    -> GeometryExtractor_2
GeometryExtractor_2
    KIND_LONG = FME Binary
    ATTR = g0
    -> LengthCalculator_2
LengthCalculator_2
    DIM = 3
    MULT = 1
    LEN_ATTR = _lengthd
    -> AnchoredSnapper [CANDIDATE]
AnchoredSnapper_Anchor (input)
    -> AnchoredSnapper [ANCHOR]
AnchoredSnapper
    EXTEND_LINES = NEVER
    SNAPTYPE_PARAM = End Point Snapping
    TOLERANCE = 0.1
    SNAPPED -> LengthCalculator
    UNTOUCHED -> LengthCalculator
LengthCalculator
    DIM = 3
    MULT = 1
    LEN_ATTR = _length
    -> Tester
Tester
    TEST_CLAUSE = NUM_TEST @Value(_length) > 0.00
    BOOL_OP = OR
    TEST_MODE = Automatic
    TEST_DESCRIPTION = ""
    PASSED -> DuplicateRemover
DuplicateRemover
    KEYATTR = geodb_oid g0
    UNIQUE -> Tester_Passed (output)
Tester_Passed (output)
