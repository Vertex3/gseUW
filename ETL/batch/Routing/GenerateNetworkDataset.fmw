FME workspace GenerateNetworkDataset.fmw

Parameters:
- DestDataset_GEODATABASE_FILE = $(FME_MF_DIR)Routing.gdb   # Destination Esri File Geodatabase
- GEODATABASE_SDE_IN_RT = C:\apps\Gizinta\gseUW\ETL\serverConfig\GIS Production.sde   # Connection File
- GEODATABASE_SDE_IN_CONNECTION_FILE_NAV = C:\Apps\Gizinta\gseUW\ETL\serverConfig\GIS Publication.sde   # Connection File
- ProductionConnectionFile = C:\Apps\Gizinta\gseUW\ETL\serverConfig\GIS Production.sde   # SDE Connection File |*.sde Production Connection File
- SourceDataset_GEODATABASE_SDE = sde   # Source Esri ArcSDE Geodatabase Dataset

Readers:
- GEODATABASE_SDE_1: GEODATABASE_SDE from $(SourceDataset_GEODATABASE_SDE)
- GEODATABASE_SDE_2: GEODATABASE_SDE

Writers:
- GEODATABASE_FILE_1: GEODATABASE_FILE to $(DestDataset_GEODATABASE_FILE)

DBO.NAV_POI (reader GEODATABASE_SDE_2)
    attributes: OBJECTID integer, NAME char(50), DESCRIPTION char(200), OWNERGROUP char(50), FLOORID char(60), POITYPE char(50), VERIFIED char(50), FEATURED char(50), TAGS char(2000), URLLINK char(100), CREATEDBY char(50), CREATEDATE date, EDITEDBY char(50), EDITDATE date, POIID char(50)
    -> BulkAttributeRenamer
BulkAttributeRenamer
    ATTRCHOICE = All Attributes
    PATTERN_ACTION_DISP = CASECHANGE
    CASE_CHANGE_TYPE = upper
    MODE_CHOICE = RENAME
    -> NeighborFinder_2 [BASE]
DBO.FloorPage (reader GEODATABASE_SDE_1)
    attributes: FLOORID char(60), FLOORCODE char(20), NAMESHORT char(50), NAMELONG char(100), SCHELEV integer, GROUNDELEV double, FLOORLEVEL integer, STACKLEVEL double, SENSITIVITY char(30), CALCROT double, LOCALROT double, DDPFLOORSORT char(71), BUILDINGID char(60), SITEID char(60), SOURCEDWG char(60), LASTUPDATE date, LASTEDITOR char(30), OBJECTID integer
    -> AttributeRenamer_3
AttributeRenamer_3
    ATTR_LIST = FLOORCODE,FLOOR,"",FLOORLEVEL,VERTORDER,"",GROUNDELEV,ELEVATION,""
    -> BoundsExtractor
BoundsExtractor
    YMIN = YMIN
    ZMIN = ZMIN
    XMIN = XMIN
    ZMAX = ZMAX
    XMAX = XMAX
    YMAX = YMAX
    -> floorinfo (writer GEODATABASE_FILE_1)
floorinfo (writer GEODATABASE_FILE_1)
    attributes: BUILDINGID char(10), FLOORID char(10), FLOOR char(10), VERTORDER integer, ELEVATION integer, XMIN double, YMIN double, XMAX double, YMAX double
DBO.RT_LineRmConnector (reader GEODATABASE_SDE_1)
    attributes: OBJECTID integer, SITEID char(60), BUILDINGID char(60), FLOORCODE char(60), FLOORID char(60), ROOMNUMBER char(26), SPACEID char(25), ADA smallint, FITNESS smallint, ACTIVE smallint, ISPUBLIC smallint, SURFACE char(255), SPEED double, WIDTH double, HEIGHT double, NAME char(255), ONEWAY char(255), EMERGENCY char(255), FROMFLOOR char(255), TOFLOOR char(255), ROUTECLASS smallint, SOURCEID char(30), SOURCEDWG char(60), LASTUPDATE date, LASTEDITOR char(30), SHAPE.STLength() double
    -> AttributeCreator
AttributeCreator
    ATTR_LIST = ROUTE_WEIGHT,3,WAYCLASS,11,ADA,1
    -> AttributeCopier
DBO.RT_LineInterior (reader GEODATABASE_SDE_1)
    attributes: OBJECTID integer, SITEID char(60), BUILDINGID char(60), FLOORCODE char(60), FLOORID char(60), SpaceID char(50), ADA smallint, EVAC char(255), FITNESS smallint, ACTIVE smallint, ISPUBLIC smallint, SURFACE char(255), SPEED double, NAME char(255), WIDTH double, HEIGHT double, ONEWAY char(255), EMERGENCY char(255), FROMFLOOR char(255), TOFLOOR char(255), ROUTECLASS smallint, SOURCEID char(30), SOURCEDWG char(60), LASTUPDATE date, LASTEDITOR char(30), SHAPE.STLength() double
    -> AttributeCreator_2
AttributeCreator_2
    ATTR_LIST = ROUTE_WEIGHT,3,WAYCLASS,10,ADA,1
    -> AttributeCopier
DBO.RT_LineTransition (reader GEODATABASE_SDE_1)
    attributes: OBJECTID integer, SITEID char(60), BUILDINGID char(60), FLOORCODE char(60), FLOORID char(60), SPACEID char(50), ADA smallint, EVAC char(255), FITNESS smallint, ACTIVE smallint, ISPUBLIC smallint, SURFACE char(255), SPEED double, NAME char(255), WIDTH double, HEIGHT double, ONEWAY char(255), EMERGENCY char(255), FROMFLOOR char(255), TOFLOOR char(255), ROUTECLASS smallint, SOURCEID char(30), SOURCEDWG char(60), LASTUPDATE date, LASTEDITOR char(30), SHAPE.STLength() double
    -> AttributeCreator_4
AttributeCreator_4
    ATTR_LIST = ROUTE_WEIGHT,3,WAYCLASS,12,ADA,0
    -> Elevator
Elevator: Tester
    BOOL_OP = OR
    TEST_CLAUSE = TEST @Value(SPACEID) CONTAINS EL
    TEST_DESCRIPTION = ""
    TEST_MODE = Automatic
    PASSED -> AttributeCreator_12
    FAILED -> AttributeCopier
AttributeCreator_12
    ATTR_LIST = WAYCLASS,14,ADA,1
    -> AttributeCopier
DBO.RT_RoomPoint (reader GEODATABASE_SDE_1)
    attributes: OBJECTID integer, SITEID char(60), BUILDINGID char(60), FLOORCODE char(60), FLOORID char(60), ROOMNUMBER char(26), SPACEID char(25), ADA smallint, FITNESS smallint, ACTIVE smallint, ISPUBLIC smallint, NAME char(255), EMERGENCY char(255), SOURCEID char(30), SOURCEDWG char(60), LASTUPDATE date, LASTEDITOR char(30)
    -> TestFilter_2
TestFilter_2
    DEFAULT_VALUE = <UNFILTERED>
    TEST_LIST = BOOL_OP,OR,COMPOSITE_TEST,<Unused>,TEST_CLAUSE,"TEST @Value(ROOMNUMBER) CONTAINS EL",Elevator,BOOL_OP,OR,COMPOSITE_TEST,<Unused>,TEST_CLAUSE,"TEST @Value(ROOMNUMBER) CONTAINS ST",Stairs
    Elevator -> Elevator_2
    Stairs -> Stairs
Elevator_2: AttributeCreator
    ATTR_LIST = WAYPOINTCLASS,14
    -> AttributeCopier_2
Stairs: AttributeCreator
    ATTR_LIST = WAYPOINTCLASS,12
    -> AttributeCopier_2
DBO.RT_DoorPoint (reader GEODATABASE_SDE_1)
    attributes: OBJECTID integer, SITEID char(60), BUILDINGID char(60), FLOORCODE char(60), FLOORID char(60), DOOR char(20), DOORID char(33), SPACEID1 char(50), SPACEID2 char(50), ADA smallint, FITNESS smallint, ACTIVE smallint, ISPUBLIC smallint, WIDTH double, HEIGHT double, NAME char(255), EMERGENCY char(255), DELAY double, SUNTIMEWINDOWSTART date, SUNTIMEWINDOWEND date, MONTIMEWINDOWSTART date, MONTIMEWINDOWEND date, TUESTIMEWINDOWSTART date, TUESTIMEWINDOWEND date, WEDTIMEWINDOWSTART date, WEDTIMEWINDOWEND date, THURSTIMEWINDOWSTART date, THURSTIMEWINDOWEND date, FRITIMEWINDOWSTART date, FRITIMEWINDOWEND date,
      SATTIMEWINDOWSTART date, SATTIMEWINDOWEND date, SOURCEID char(30), SOURCEDWG char(60), LASTUPDATE date, LASTEDITOR char(30)
    -> AttributeCopier_3
AttributeCopier_3
    ATTR_LIST = BUILDINGID,FACILITYID,""
    -> AttributeRenamer_4
AttributeRenamer_4
    ATTR_LIST = FITNESS,ISFITNESS,"",FLOORCODE,FLOOR,"",ADA,ISADA,"",ACTIVE,ISACTIVE,""
    -> CoordinateExtractor_4
CoordinateExtractor_4
    Y_ATTR = _y0
    Z_ATTR = ELEVATION
    IND = 0
    Z_DEFAULT = 0
    X_ATTR = _x0
    -> AttributeCreator_8
AttributeCreator_8
    ATTR_LIST = ROUTE_WEIGHT,2
    -> CoordinateRounder_3
CoordinateRounder_3
    XPREC = 4
    YPREC = 4
    ZPREC = 4
    ROUNDED -> door (writer GEODATABASE_FILE_1)
door (writer GEODATABASE_FILE_1)
    attributes: geodb_oid integer, OBJECTID integer, FACILITYID char(20), BUILDINGID char(10), FLOORID char(15), FLOOR char(12), NAME char(255), DELAY double, EMERGENCY char(255), ISACTIVE smallint, ISADA smallint, ISFITNESS smallint, ISPUBLIC smallint, WIDTH double, HEIGHT double, MONTIMEWINDOWEND date, MONTIMEWINDOWSTART date, TUESTIMEWINDOWEND date, TUESTIMEWINDOWSTART date, WEDTIMEWINDOWEND date, WEDTIMEWINDOWSTART date, THURSTIMEWINDOWEND date, THURSTIMEWINDOWSTART date, FRITIMEWINDOWEND date, FRITIMEWINDOWSTART date, SATTIMEWINDOWEND date, SATTIMEWINDOWSTART date, SUNTIMEWINDOWEND date, SUNTIMEWINDOWSTART date, ELEVATION smallint,
      ROUTE_WEIGHT smallint
DBO.RT_LineExterior (reader GEODATABASE_SDE_1)
    attributes: OBJECTID integer, ADA smallint, FITNESS smallint, ACTIVE smallint, SURFACE char(255), SPEED double, NAME char(255), WIDTH double, HEIGHT double, ISPUBLIC smallint, ONEWAY char(255), EMERGENCY char(255), FROMFLOOR char(255), TOFLOOR char(255), ROUTECLASS smallint, SOURCEID char(30), SOURCEDWG char(60), LASTUPDATE date, LASTEDITOR char(30), SHAPE.STLength() double
    -> AttributeCreator_3
AttributeCreator_3
    ATTR_LIST = ROUTE_WEIGHT,5,WAYCLASS,17,ADA,1
    -> AttributeCopier
DBO.RT_BuildingConnector (reader GEODATABASE_SDE_1)
    attributes: geodb_oid integer, OBJECTID_1 integer, OBJECTID integer, ADA integer, FITNESS integer, ACTIVE integer, SURFACE char(254), SPEED double, NAME char(254), WIDTH double, HEIGHT double, ISPUBLIC integer, ONEWAY char(254), EMERGENCY char(254), FROMFLOOR char(254), TOFLOOR char(254), ROUTECLASS integer, SHAPE_STLe double, SHAPE_Length double, SHAPE_1.STLength() double
    -> AttributeCreator_9
AttributeCreator_9
    ATTR_LIST = ROUTE_WEIGHT,5,WAYCLASS,17,ADA,1
    -> AttributeCopier
AttributeCopier
    ATTR_LIST = BUILDINGID,FACILITYID,"",FROMFLOOR,FROMFLOORID,"",TOFLOOR,TOFLOORID,""
    -> AttributeRenamer
AttributeRenamer
    ATTR_LIST = FITNESS,ISFITNESS,"",FLOORCODE,FLOOR,"",ADA,ISADA,"",ACTIVE,ISACTIVE,""
    -> CoordinateExtractor
CoordinateExtractor
    Y_ATTR = _y0
    Z_ATTR = FROMELEVATION
    IND = 0
    Z_DEFAULT = 0
    X_ATTR = _x0
    -> CoordinateCounter
CoordinateCounter
    CNT_ATTR = _coordcount
    -> CoordinateExtractor_2
CoordinateExtractor_2
    Y_ATTR = _yn
    Z_ATTR = TOELEVATION
    IND = @Value(_coordcount) - 1
    Z_DEFAULT = 0
    X_ATTR = _xn
    -> LengthCalculator
LengthCalculator
    LEN_ATTR = LENGTH_METER
    MULT = 1
    DIM = 2
    -> CoordinateRounder
CoordinateRounder
    XPREC = 4
    YPREC = 4
    ZPREC = 4
    ROUNDED -> way (writer GEODATABASE_FILE_1)
    ROUNDED -> FloorLookup (writer GEODATABASE_FILE_1)
way (writer GEODATABASE_FILE_1)
    attributes: FACILITYID char(20), BUILDINGID char(10), NAME char(255), WAYCLASS smallint, FLOORID char(15), FLOOR char(12), FROMFLOORID char(15), TOFLOORID char(15), FROMELEVATION smallint, TOELEVATION smallint, SPEED double, ONEWAY char(2), EMERGENCY char(50), ISADA smallint, ISFITNESS smallint, ISACTIVE smallint, ISPUBLIC smallint, WIDTH double, HEIGHT double, LENGTH_METER double, ROUTE_WEIGHT smallint
FloorLookup (writer GEODATABASE_FILE_1)
    attributes: BUILDINGID char(50), FLOOR char(5), FROMFLOOR char(5), TOFLOOR char(5), FLOORID char(50)
DBO.NAV_Redacted (reader GEODATABASE_SDE_2)
    attributes: OBJECTID integer, FLOORID char(60), CreatedBy char(50), CreateDate date, EditedBy char(50), EditDate date, Reason char(100), FLOORCODE char(50), GroupOwner char(50), RedactFloorplan char(50), SHAPE.STArea() double, SHAPE.STLength() double
    -> NeighborFinder_2 [CANDIDATE]
NeighborFinder_2
    GROUP_BY = FLOORID
    CANDIDATES_FIRST = No
    ATTR_CONFLICT_RES = Use Base
    MODE = Bases and Candidates
    MAX = 0.1
    CLOSE_LIST_NAME = _close
    K = 1
    INSERT_VERTEX = No
    ATTR_ACCUM_MODE = Merge Candidate
    TREAT_POLYGON_AS = Areas
    MATCHED -> Redacted
    UNMATCHED_BASE -> CoordinateRounder_4
Redacted: Inspector [off]
CoordinateRounder_4
    XPREC = 4
    YPREC = 4
    ZPREC = 4
    ROUNDED -> AttributeSplitter
AttributeSplitter
    ATTR_NAME = TAGS
    DROP_EMPTY_PARTS = No
    DELIMITER = ,
    LIST_NAME = _tags
    TRIM_OPTION = Both
    -> AttributeCreator_5
AttributeCreator_5
    ATTR_TABLE:
      SET_TO TAG_1 = @Value(_tags{0})
      SET_TO TAG_2 = @Value(_tags{1})
      SET_TO TAG_3 = @Value(_tags{2})
      SET_TO TAG_4 = @Value(_tags{3})
      SET_TO TAG_5 = @Value(_tags{4})
      SET_TO POINAME = @Value(NAME)
      SET_TO FEATURETYPE = @Value(POITYPE)
    -> SubstringExtractor
SubstringExtractor
    RESULT_ATTR = BUILDINGID
    SRC_STRING = @Value(FLOORID)
    END = -1
    START = FME_CONDITIONAL:DEFAULT_VALUE'0'BOOL_OP;OR;COMPOSITE_TEST;<Unused>;TEST @Value(FLOORID) CONTAINS _'@FindString(@Value(FLOORID),'_')+1'FME_NUM_CONDITIONS2___
    -> BoundsExtractor_2
BoundsExtractor_2
    YMIN = YMIN
    ZMIN = _zmin
    XMIN = XMIN
    ZMAX = _zmax
    XMAX = XMAX
    YMAX = YMAX
    -> CoordinateExtractor_5
CoordinateExtractor_5
    MODE = Specify Coordinate
    Y_ATTR = DISPLAY_Y
    Z_ATTR = DISPLAY_Z
    IND = 0
    X_ATTR = DISPLAY_X
    -> poi (writer GEODATABASE_FILE_1)
poi (writer GEODATABASE_FILE_1)
    attributes: SITEID char(20), SITENAME char(50), BUILDINGID char(50), BUILDINGNAME char(100), FLOORID char(50), FLOORNAME char(50), ROOMID char(50), ROOMNAME char(50), POIID char(50), POINAME char(50), TAG_1 char(255), TAG_2 char(255), TAG_3 char(255), TAG_4 char(255), TAG_5 char(255), FEATURETYPE char(20), XMIN double, YMIN double, XMAX double, YMAX double, FEATURED smallint, DISPLAY_X double, DISPLAY_Y double, DISPLAY_Z integer, URLLINK char(200)
PointBarrier (writer GEODATABASE_FILE_1)
    attributes: geodb_oid integer, OBJECTID integer, NAME char(50), BARRIERTYPE smallint, FULLEDGE smallint, ATTR_WALKTIME double, CURBAPPROACH smallint, ATTR_LENGTH double
DBO.RT_Waypoint (reader GEODATABASE_SDE_1) [off]
    attributes: OBJECTID integer, SITEID char(60), BUILDINGID char(60), FLOORCODE char(60), FLOORID char(60), ACTIVE smallint, ISPUBLIC smallint, NAME char(255), WAYPOINTTYPE char(20), SOURCEID char(30), SOURCEDWG char(60), LASTUPDATE date, LASTEDITOR char(30)
    -> TestFilter
TestFilter
    DEFAULT_VALUE = <UNFILTERED>
    TEST_LIST = BOOL_OP,OR,COMPOSITE_TEST,<Unused>,TEST_CLAUSE,"TEST @Value(WAYPOINTTYPE) = Elevator",Elevator,BOOL_OP,OR,COMPOSITE_TEST,<Unused>,TEST_CLAUSE,"TEST @Value(WAYPOINTTYPE) = Floor Transition",Stairs
Other: AttributeCreator
    ATTR_LIST = WAYPOINTCLASS,4
    -> AttributeCopier_2
AttributeCopier_2
    ATTR_LIST = BUILDINGID,FACILITYID,"",FLOORCODE,FLOOR,""
    -> CoordinateExtractor_3
CoordinateExtractor_3
    Y_ATTR = _y0
    Z_ATTR = ELEVATION
    IND = 0
    Z_DEFAULT = 0
    X_ATTR = _x0
    -> CoordinateRounder_2
CoordinateRounder_2
    XPREC = 4
    YPREC = 4
    ZPREC = 4
    ROUNDED -> waypoint (writer GEODATABASE_FILE_1)
waypoint (writer GEODATABASE_FILE_1)
    attributes: FACILITYID char(20), BUILDINGID char(10), FLOORID char(15), FLOOR char(12), NAME char(150), ELEVATION smallint, WAYPOINTCLASS integer
CoordinateRounder_6
    XPREC = 4
    YPREC = 4
    ZPREC = 4
    ROUNDED -> floor (writer GEODATABASE_FILE_1)
floor (writer GEODATABASE_FILE_1) [off]
    attributes: OBJECTID integer, BUILDINGID char(10), FLOORID char(10)

Bookmark: Footprint
CoordinateRounder_5
    XPREC = 4
    YPREC = 4
    ZPREC = 4
    ROUNDED -> footprint (writer GEODATABASE_FILE_1)
footprint (writer GEODATABASE_FILE_1) [off]
    attributes: BUILDINGID char(4)

Bookmark: Waypoint
Note: Filter out if no RT drawings
Note: Might add door waypoints and others

Bookmark: POI and Barrier
Note: construct barriers from project area and other polygons/status
