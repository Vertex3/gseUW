FME workspace RT_Extract.fmw

Parameters:
- FEATURE_TYPES = DBO.RT_DoorPoint DBO.RT_LineInterior DBO.RT_LineRmConnector DBO.RT_LineTransition DBO.RT_RoomPoint DBO.RT_Stop DBO.RT_Turn DBO.RT_LineExterior
- Extract_Since = 20170620084600   # Extract Buildings since this date
- DestDataset_ACAD = C:\Vault_Mirror\BatchGIS\Export\RT_Extract.dwg   # Destination Autodesk AutoCAD DWG/DXF File

Readers:
- GEODATABASE_SDE_1: GEODATABASE_SDE
- GEODATABASE_SDE_2: GEODATABASE_SDE

Writers:
- ACAD_1: ACAD to $(DestDataset_ACAD)

DBO.RT_LineExterior (reader GEODATABASE_SDE_2)
    attributes: OBJECTID integer, ADA smallint, FITNESS smallint, ACTIVE smallint, SURFACE char(255), SPEED double, NAME char(255), WIDTH double, HEIGHT double, ISPUBLIC smallint, ONEWAY char(255), EMERGENCY char(255), FROMFLOOR char(255), TOFLOOR char(255), ROUTECLASS smallint, SOURCEID char(30), SOURCEDWG char(60), LASTUPDATE date, LASTEDITOR char(30), SHAPE.STLength() double
    -> DBO.RT_Waypoint (writer ACAD_1)
Note: Tried a few ways to have SQL where clause but did not work easily...
DBO.RT_Waypoint (reader GEODATABASE_SDE_1)
    attributes: OBJECTID integer, SITEID char(60), BUILDINGID char(60), FLOORCODE char(60), FLOORID char(60), ACTIVE smallint, ISPUBLIC smallint, NAME char(255), WAYPOINTTYPE char(20), SOURCEID char(30), SOURCEDWG char(60), LASTUPDATE date, LASTEDITOR char(30), SURFACE char(255), DOORID char(33), ADA smallint, ROUTECLASS smallint, TUESTIMEWINDOWSTART date, EVAC char(255), FRITIMEWINDOWSTART date, Edge4FCID integer, FRITIMEWINDOWEND date, ROOMNUMBER char(26), SpaceID char(50), SHAPE.STLength() double, SPACEID2 char(50), Edge1Pos double, FITNESS smallint, Edge5FID integer, ONEWAY char(255),
      Edge2FCID integer, WEDTIMEWINDOWEND date, Edge4FID integer, MONTIMEWINDOWSTART date, SPACEID1 char(50), DELAY double, SPEED double, EMERGENCY char(255), Edge2Pos double, Edge1FID integer, Edge1FCID integer, FROMFLOOR char(255), TOFLOOR char(255), Edge4Pos double, SUNTIMEWINDOWSTART date, WIDTH double, SPACEID char(25), Edge2FID integer, Edge3FID integer, Edge1End char(1), THURSTIMEWINDOWEND date, HEIGHT double, SATTIMEWINDOWSTART date, Edge5FCID integer, SUNTIMEWINDOWEND date, Edge3Pos double, Edge5Pos double, Edge3FCID integer, WEDTIMEWINDOWSTART date, THURSTIMEWINDOWSTART date,
      SATTIMEWINDOWEND date, TUESTIMEWINDOWEND date, MONTIMEWINDOWEND date, DOOR char(20)
    -> ExteriorLines
Note: Had to leave this in or caused writer error on line exterior schema...
ExteriorLines: Tester
    TEST_DESCRIPTION = ""
    TEST_MODE = Automatic
    BOOL_OP = OR
    TEST_CLAUSE = TEST @Value(fme_feature_type) CONTAINS RT_LineExterior
    FAILED -> MaxBuildingDate
    FAILED -> FeatureMerger [input 1]
MaxBuildingDate: StatisticsCalculator
    STDEVP_ATTR = _stdevp
    STATS_ATTRS = LASTUPDATE
    MAX_ATTR = _maxLastUpdate
    NUMERIC_ATTR = _numeric_count
    MODE_ATTR = _mode
    MEAN_ATTR = _mean
    MIN_ATTR = _min
    STDEV_ATTR = _stdev
    COUNT_ATTR = _count
    PREPEND_ATTR_NAME_CHOICE = For multiple results only
    GROUP_BY = BUILDINGID
    RANGE_ATTR = _range
    MEDIAN_ATTR = _median
    COMPUTE_HISTOGRAM = NO
    SUM_ATTR = _sum
    SUMMARY -> TestFilterSince
TestFilterSince
    TEST_LIST = BOOL_OP,OR,COMPOSITE_TEST,<Unused>,TEST_CLAUSE,"TEST @Value(_maxLastUpdate) > $(Extract_Since)",@Value(_maxLastUpdate) > __Extract_Since_
    DEFAULT_VALUE = <UNFILTERED>
    @Value(_maxLastUpdate) > __Extract_Since_ -> FeatureMerger [input 2]
FeatureMerger
    PROCESS_DUPS = No
    SUPPLIERS_FIRST = No
    ATTR_ACCUM_MODE = Merge Supplier
    MERGE_TYPE = Attributes Only
    ATTR_CONFLICT_RES = Use Requestor
    IGNORE_NULLS = No
    JOIN_KEYS = @Value(BUILDINGID) @Value(BUILDINGID) AUTO
    REJECT_NULL_MISSING_KEYS = No
    MERGED -> DBO.RT_Waypoint (writer ACAD_1)
DBO.RT_Waypoint (writer ACAD_1)
    attributes: OBJECTID number(11,0), SITEID char(60), BUILDINGID char(60), FLOORCODE char(60), FLOORID char(60), ACTIVE number(6,0), ISPUBLIC number(6,0), NAME char(255), WAYPOINTTYPE char(20), SOURCEID char(30), SOURCEDWG char(60), LASTUPDATE char(20), LASTEDITOR char(30), SURFACE char(255), DOORID char(33), ADA number(6,0), ROUTECLASS number(6,0), TUESTIMEWINDOWSTART char(20), EVAC char(255), FRITIMEWINDOWSTART char(20), Edge4FCID number(11,0), FRITIMEWINDOWEND char(20), ROOMNUMBER char(26), SpaceID char(50), SHAPE_STLength__ number(31,15), SPACEID2 char(50), Edge1Pos number(31,15), FITNESS number(6,0), Edge5FID number(11,0), ONEWAY char(255),
      Edge2FCID number(11,0), WEDTIMEWINDOWEND char(20), Edge4FID number(11,0), MONTIMEWINDOWSTART char(20), SPACEID1 char(50), DELAY number(31,15), SPEED number(31,15), EMERGENCY char(255), Edge2Pos number(31,15), Edge1FID number(11,0), Edge1FCID number(11,0), FROMFLOOR char(255), TOFLOOR char(255), Edge4Pos number(31,15), SUNTIMEWINDOWSTART char(20), WIDTH number(31,15), SPACEID char(25), Edge2FID number(11,0), Edge3FID number(11,0), Edge1End char(1), THURSTIMEWINDOWEND char(20), HEIGHT number(31,15), SATTIMEWINDOWSTART char(20), Edge5FCID number(11,0), SUNTIMEWINDOWEND char(20), Edge3Pos number(31,15), Edge5Pos number(31,15), Edge3FCID number(11,0), WEDTIMEWINDOWSTART char(20), THURSTIMEWINDOWSTART char(20),
      SATTIMEWINDOWEND char(20), TUESTIMEWINDOWEND char(20), MONTIMEWINDOWEND char(20), DOOR char(20)
