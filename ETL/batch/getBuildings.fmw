FME workspace getBuildings.fmw

Parameters:
- SourceDataset_ESRIMSD = C:\Apps\Gizinta\gseUW\CAD\Siteplan\**\*.dwg   # Source Autodesk AutoCAD DWG/DXF File(s)
- DestDataset_FILEGDB = $(FME_MF_DIR)bldgs.gdb   # Destination Geodatabase
- SourceDataset_GEODATABASE_SDE = sde   # Source Esri ArcSDE Geodatabase Dataset

Readers:
- ESRIMSD_1: ESRIMSD from $(SourceDataset_ESRIMSD) in EPSG:2285
- GEODATABASE_SDE_1: GEODATABASE_SDE from $(SourceDataset_GEODATABASE_SDE)

Writers:
- FILEGDB_1: FILEGDB to $(DestDataset_FILEGDB)

Building (reader ESRIMSD_1)
    attributes: FACNUM char(255), RULEID char(255), msd_feature_class_name
    -> AttributeFilter
AttributeFilter
    ATTR_NAME = FACNUM
    ATTR_VALUES = <EMPTY>,<MISSING>,<NULL>,<UNFILTERED>,0000
    <UNFILTERED> -> DuplicateRemover
DBO.Building_Outline_Tilt (reader GEODATABASE_SDE_1)
    attributes: geodb_oid integer, OBJECTID integer, SITEID char(60), BUILDINGID char(60), CALCROT double, SOURCEID char(30), SOURCEDWG char(60), LASTUPDATE date, LASTEDITOR char(30), BLDGNAME char(100), SHAPE.STArea() double, SHAPE.STLength() double
    -> AttributeSplitter
AttributeSplitter
    LIST_NAME = _list
    ATTR_NAME = BUILDINGID
    DELIMITER = _
    TRIM_OPTION = Both
    DROP_EMPTY_PARTS = No
    -> AttributeCreator
AttributeCreator
    ATTR_LIST = FACNUM,@Value(_list{1})
    -> DuplicateRemover
DuplicateRemover
    KEYATTR = FACNUM
    UNIQUE -> Building (writer FILEGDB_1)
Building (writer FILEGDB_1)
    attributes: FACNUM text(255)
