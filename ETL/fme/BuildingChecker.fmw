FME workspace BuildingChecker.fmw

Readers:
- GEODATABASE_SDE_1: GEODATABASE_SDE

DBO.RT_LineInterior (reader GEODATABASE_SDE_1)
    attributes: OBJECTID integer, SITEID char(60), BUILDINGID char(60), FLOORCODE char(60), FLOORID char(60), SpaceID char(50), ADA smallint, EVAC char(255), FITNESS smallint, ACTIVE smallint, ISPUBLIC smallint, SURFACE char(255), SPEED double, NAME char(255), WIDTH double, HEIGHT double, ONEWAY char(255), EMERGENCY char(255), FROMFLOOR char(255), TOFLOOR char(255), ROUTECLASS smallint, SOURCEID char(30), SOURCEDWG char(60), LASTUPDATE date, LASTEDITOR char(30), SHAPE.STLength() double
    -> AttributeCreator_2
DBO.RT_LineRmConnector (reader GEODATABASE_SDE_1)
    attributes: OBJECTID integer, SITEID char(60), BUILDINGID char(60), FLOORCODE char(60), FLOORID char(60), ROOMNUMBER char(26), SPACEID char(25), ADA smallint, FITNESS smallint, ACTIVE smallint, ISPUBLIC smallint, SURFACE char(255), SPEED double, WIDTH double, HEIGHT double, NAME char(255), ONEWAY char(255), EMERGENCY char(255), FROMFLOOR char(255), TOFLOOR char(255), ROUTECLASS smallint, SOURCEID char(30), SOURCEDWG char(60), LASTUPDATE date, LASTEDITOR char(30), SHAPE.STLength() double
    -> AttributeCreator_2
DBO.RT_LineTransition (reader GEODATABASE_SDE_1)
    attributes: OBJECTID integer, SITEID char(60), BUILDINGID char(60), FLOORCODE char(60), FLOORID char(60), SPACEID char(50), ADA smallint, EVAC char(255), FITNESS smallint, ACTIVE smallint, ISPUBLIC smallint, SURFACE char(255), SPEED double, NAME char(255), WIDTH double, HEIGHT double, ONEWAY char(255), EMERGENCY char(255), FROMFLOOR char(255), TOFLOOR char(255), ROUTECLASS smallint, SOURCEID char(30), SOURCEDWG char(60), LASTUPDATE date, LASTEDITOR char(30), SHAPE.STLength() double
    -> AttributeCreator_2
AttributeCreator_2
    ATTR_TABLE = SET_TO BLDG = @Value(BUILDINGID)
    -> CoordinateExtractor
    -> NeighborFinder [CANDIDATE]
    -> NeighborFinder_2 [CANDIDATE]
CoordinateExtractor
    IND = 0
    MODE = Specify Coordinate
    Z_ATTR = _z0
    Y_ATTR = _y0
    X_ATTR = _x0
    -> CoordinateCounter
CoordinateCounter
    CNT_ATTR = _n
    -> CoordinateExtractor_2
CoordinateExtractor_2
    IND = @Value(_n)-1
    MODE = Specify Coordinate
    Z_ATTR = _zn
    Y_ATTR = _yn
    X_ATTR = _xn
    -> GeometryExtractor
GeometryExtractor
    ATTR = _geometry
    ELLIPSOID_NAME = WGS84
    MSSQL_FORMAT_CHOICE = Geometry
    OGCVERSION = 1.2
    LETTERING = WGS84
    OMIT_NAMESPACES_DISPLAY = No
    OGC_WKT_PRECISION_DISPLAY = Shortened 64-bit
    PREFER_POLYGON_OVER_SURFACE = No
    GEOHASH_PRECISION_DISPLAY = ~9.3 mm (12 characters)
    LEVELS_ATTR = _levels
    PRECISION = 0
    OGEOSMS_URL_PREFIX = http://maps.google.com/?q=
    ISO6709_FORMAT_CHOICE = Degrees and Decimal Degrees
    KIND_LONG = FME Binary
    REMOVE_GEOMETRY = No
    ISO6709_MAX_DECIMAL_PLACES = 5
    -> VertexCreator_n
    -> VertexCreator_0
VertexCreator_0
    ZVAL = @Value(_z0)
    YVAL = @Value(_y0)
    XVAL = @Value(_x0)
    MODE_NAME = Replace with Point
    -> NeighborFinder_2 [BASE]
VertexCreator_n
    ZVAL = @Value(_zn)
    YVAL = @Value(_yn)
    XVAL = @Value(_xn)
    MODE_NAME = Replace with Point
    -> NeighborFinder_2 [BASE]
DBO.RT_RoomPoint (reader GEODATABASE_SDE_1)
    attributes: OBJECTID integer, SITEID char(60), BUILDINGID char(60), FLOORCODE char(60), FLOORID char(60), ROOMNUMBER char(26), SPACEID char(25), ADA smallint, FITNESS smallint, ACTIVE smallint, ISPUBLIC smallint, NAME char(255), EMERGENCY char(255), SOURCEID char(30), SOURCEDWG char(60), LASTUPDATE date, LASTEDITOR char(30)
    -> AttributeCreator
DBO.RT_DoorPoint (reader GEODATABASE_SDE_1)
    attributes: OBJECTID integer, SITEID char(60), BUILDINGID char(60), FLOORCODE char(60), FLOORID char(60), DOOR char(20), DOORID char(33), SPACEID1 char(50), SPACEID2 char(50), ADA smallint, FITNESS smallint, ACTIVE smallint, ISPUBLIC smallint, WIDTH double, HEIGHT double, NAME char(255), EMERGENCY char(255), DELAY double, SUNTIMEWINDOWSTART date, SUNTIMEWINDOWEND date, MONTIMEWINDOWSTART date, MONTIMEWINDOWEND date, TUESTIMEWINDOWSTART date, TUESTIMEWINDOWEND date, WEDTIMEWINDOWSTART date, WEDTIMEWINDOWEND date, THURSTIMEWINDOWSTART date, THURSTIMEWINDOWEND date, FRITIMEWINDOWSTART date, FRITIMEWINDOWEND date,
      SATTIMEWINDOWSTART date, SATTIMEWINDOWEND date, SOURCEID char(30), SOURCEDWG char(60), LASTUPDATE date, LASTEDITOR char(30)
    -> AttributeCreator
AttributeCreator
    ATTR_TABLE = SET_TO BLDG = @Value(BUILDINGID)
    -> NeighborFinder [BASE]
    -> NeighborFinder_2 [CANDIDATE]
NeighborFinder
    ATTR_ACCUM_MODE = Merge Candidate
    INSERT_VERTEX = No
    CANDIDATES_FIRST = No
    ATTR_CONFLICT_RES = Use Base
    TREAT_POLYGON_AS = Lines
    MAX = 0.0001
    K = 1
    GROUP_BY = FLOORID
    MODE = Bases and Candidates
    MATCHED -> Matched_Node
    UNMATCHED_BASE -> Orphan_Node
Matched_Node: Inspector
Orphan_Node: Inspector
NeighborFinder_2
    ATTR_ACCUM_MODE = Merge Candidate
    CLOSE_LIST_ATTRS_TO_INCLUDE = OBJECTID
    INSERT_VERTEX = No
    CANDIDATES_FIRST = No
    ATTR_CONFLICT_RES = Use Base
    TREAT_POLYGON_AS = Lines
    MAX = 0.0001
    K = 2
    GROUP_BY = FLOORID
    CLOSE_LIST_NAME = _candidates
    MODE = Bases and Candidates
    CLOSE_LIST_ATTRS_TO_INCLUDE_MODE = Selected Attributes
    MATCHED -> ListElementCounter
ListElementCounter
    CNT_ATTR = _element_count
    LIST_NAME = _candidates{}
    -> GeometryReplacer
GeometryReplacer
    KIND_LONG = FME Binary
    SOURCE = @Value(_geometry)
    REMOVE_ATTRIBUTE = No
    -> AttributeExposer
AttributeExposer
    ATTR_LIST = fme_feature_type,OBJECTID
    -> DuplicateFilter
DuplicateFilter
    INPUT_ORDERED_CHOICE = No
    KEYATTR = OBJECTID fme_feature_type
    UNIQUE -> DeadEnd
DeadEnd: Tester
    BOOL_OP = OR
    TEST_MODE = Automatic
    TEST_DESCRIPTION = ""
    TEST_CLAUSE = TEST @Value(_element_count) <= 1
    PASSED -> Dangling_Line
    FAILED -> Attached_Line
Dangling_Line: Inspector
Attached_Line: Inspector
