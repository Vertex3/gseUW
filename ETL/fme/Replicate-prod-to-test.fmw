FME workspace Replicate-prod-to-test.fmw

Parameters:
- FEATURE_TYPES = DBO.Basemap_Annotations DBO.BudgetCode DBO.Building DBO.Building_Table DBO.BuildingCondition DBO.BuildingLookup DBO.Buildings_Other DBO.Buildings_Simplified DBO.BuildingType DBO.Campus_Zones DBO.ConstructionFence DBO.DrawingType_Outline DBO.DrawingType_RT DBO.DrawingType_XP DBO.EmployeeAssigned DBO.EmployeeInfo DBO.Facility_Table DBO.FacilitySite DBO.Floor DBO.Floor_Level DBO.Floor_Table DBO.FloorArea DBO.FloorArea_ALL DBO.FloorLookup DBO.FloorPage DBO.FloorPage_ALL DBO.FloorPage_Wrapper DBO.FloorPage_Wrapper_ALL DBO.FloorPageTemplate DBO.FloorplanLine DBO.FloorplanLine_ALL DBO.FunctionalUse DBO.Gatehouse DBO.InteriorSpace DBO.InteriorSpace_ALL DBO.InteriorSpace_Point DBO.InteriorSpace_Point_ALL DBO.InteriorSpaceLookup DBO.Link DBO.Login DBO.LoginOrgAssignment DBO.Misc_SurfaceAreas DBO.Misc_SurfaceLines DBO.Misc_Trees DBO.Organization DBO.OrganizationCollege DBO.OrganizationDepartment DBO.OrganizationSubCollege DBO.Parking_Lot DBO.Path DBO.SpaceClassificationLevel1 DBO.SpaceClassificationLevel2 DBO.SpaceFunctionalAllocation DBO.SpaceStandard DBO.Water_Features DBO.AccessType

Readers:
- GEODATABASE_SDE_1: GEODATABASE_SDE

Writers:
- GEODATABASE_SDE_2: GEODATABASE_SDE
- GEODATABASE_SDE_3: GEODATABASE_SDE to <Unused>

DBO.Water_Features (reader GEODATABASE_SDE_1)
    attributes: OBJECTID integer, Type char(50), SHAPE.STArea() double, SHAPE.STLength() double, MOD_USER char(30), OFM_LEASE_START_DATE date, CREATE_DATE date, TextString char(255), FACILITY_CODE char(4), OPERHOURSKEY char(50), SPACECAT1ID char(5), BUILDINGNAME char(50), Shape_STLength_12 double, SPACETYPECAT1KEY char(5), created_date date, Phase char(100), OrganizationSubCollegeID char(5), BUILDINGCONDITIONID char(50), TELEPHONEEXT char(25), NAME char(255), ATTACHMENTID integer, SurfaceLine char(50), created_user char(255), ORGANIZATIONKEY char(50), OFM_SITE_CODE char(3), FLOORPAGETEMPLATE char(3), ProjectNameWithoutNumber char(255), BUDGETCODEKEY char(50), FIRSTNAME char(255), ACCESSTYPEKEY char(50),
      ORGASSIGNABLE char(5), FLOORCODE char(5), Bldg_Key integer, Description char(255), VERTORDER smallint, OCCUPANCY smallint, SymbolID integer, LOGINID char(50), SHIFT char(50), FUNCTIONALUSEKEY char(50), last_edited_date date, BUILDINGTYPE char(50), OFM_CITY_CODE char(4), OFM_HSR char(3), FACILITY_NUMBER smallint, LASTEDITOR char(30), Notes char(300), Shape.STArea() double, ROTATION double, BUILDINGCONDITION char(50), ASSIGNMENTKEY char(50), ADA char(15), SiteName char(50), FilterChangeDate date, CEOID integer, HorizontalAlignment smallint, ROOMNUMBER char(25), COSTCTR double, ModRotation range_domain(dEvac_ModRotation:double:0:360), FilterDepth smallint,
      SPACESTANDARD char(50), MOD_DATE date, CALCROT double, CONTENT_TYPE char(150), NOTES char(255), OFM_REPLACEMENT_COST_FACTOR integer, FilterQty smallint, SOURCEID char(30), FACNUM char(50), FLOORKEY char(50), OrganizationCollegeID char(3), COMMENTS char(255), ACCESSTYPE char(50), AssetRotation double, PathType char(50), SECTOR char(3), FACILITY_TYPE char(4), PERCENTASSIGNABLE double, EvacMap char(5), FIELDNAME char(64), FLOORSHORTNAME char(50), USABLEAREA double, ENTITYTYPEID char(50), Override integer, VACANCY smallint, DESCRIPTION char(255), GROUNDOFFSET double, OWNEDBY char(50), Scope char(2048), ASSIGNMENTCOUNT integer,
      EMPLOYEEID char(50), FilterLength smallint, ROOF char(10), OFM_LEGISLATIVE_DISTRICT char(2), EgressRotation range_domain(dEvac_ModRotation:double:0:360), GROUNDELEV double, DATA_SIZE integer, LONG_NAME char(100), OS_USER char(30), DEPARTMENT char(50), FloorID char(50), INTERIORSPACE char(3), KNOWNAS char(255), BUILDINGID char(50), TABLENAME char(254), LOGINKEY char(50), FSOID integer, PHOTOFILE char(100), FLOORPLANLINE char(3), Angle double, OFM_COUNTY_CODE char(3), SHORTNAME char(25), LNAMEFNAME char(140), SPACEUSECAT1KEY char(5), ASSIGNABLEAREA double, OFM_SITE_ADDRESS char(40), VACANCYRATE double, CharacterWidth double, STATUS char(3), FLOORAREA double,
      BUDGETCODE char(50), FlipAngle double, SPACEUSECAT2KEY char(5), FACILITYID char(50), CONDITIONKEY char(50), FUNCTIONALUSEID char(50), FontLeading double, FLOORLONGNAME char(100), FloorKey char(60), ADDRESS char(255), CM char(100), REGISTERED_HISTORIC_SITE char(1), MapFloorID char(50), SiteID char(50), TYPE char(20), Shape_STArea_12 double, FLOORLEVEL integer, ATT_NAME char(250), DDPEvacRot double, Name char(50), Italic smallint, DEFINITION char(256), CENTER_FACILITY_LONGITUDE double, Bold smallint, CEILINGHEIGHT double, SITEKEY smallint, Display char(50), SPACECAT2ID char(5), Status char(20), ENTITYKEY char(50),
      Comment char(255), CollegeName char(50), DepartmentName char(50), PubliclyAvailable char(5), SPACECAT1KEY char(5), VALUEINFO char(254), ORGANIZATIONID char(50), DisplayType char(50), DDPFLOORSORT char(71), FACILITYKEY char(50), CoordinateSystem smallint, VerticalAlignment smallint, SCHELEV integer, BUILDINGMANAGER char(50), ON_MANUAL smallint, PM char(2048), CENTER_FACILITY_LATITUDE double, BUILDINGS smallint, YEAR_CONSTRUCTED char(4), OutlineType char(25), DRAWINGNAME char(100), DisplayName char(255), AVAILABILITY char(50), ZOrder integer, BUILDING char(3), Lot_Number char(50), EMPLOYEEKEY char(50), Apex smallint, SPACESTANDARDKEY char(50), ASSIGNMENTCOLLEGEKEY char(3),
      LAST_MAJOR_RENOVATION_COST integer, Site char(50), LABEL char(100), OCCUPANCYRATE double, XOffset double, EMAIL char(255), NETAREA double, DENSITY double, AGGREGATE_FACILITY_NUMBER smallint, OrganizationCollegeKey char(3), LEASED_OR_OWNED char(6), ACCESSTYPEID char(50), OFM_CONDITION char(1), SPACESTANDARDID char(50), OFM_LEASE_END_DATE date, VALUEMETHOD char(254), SPACETYPECAT2KEY char(5), BUILDINGTYPEID char(50), BuildingID char(60), SOURCEDWG char(60), SITE char(7), CITY char(100), STATE char(2), BUILDINGTYPEKEY char(50), CAPACITY integer, DATA blob, CONSTRUCTION_OR_PURCHASE_COST integer, Neighborhood char(50), AVERAGEAREA smallint, RUN_WEIGHT smallint,
      USERTYPE char(255), AssetType char(50), ON_CREATE smallint, FontName char(255), YEARBUILT smallint, PERCENTUSABLE double, Underline smallint, REL_OBJECTID integer, LAST_MAJOR_RENOVATION_DATE date, ASSIGNMENTSUBCOLLEGE char(50), SPACEID char(50), EAPID double, LASTUPDATE date, COMMENTTEXT char(255), OrganizationDepartmentID char(7), FUNCTIONALUSE char(50), WEB_PLAN char(1), FeatureID integer, ASSIGNMENTDEPARTMENTKEY char(7), SubCollegeName char(50), Rotation double, ProjectID char(100), LASTNAME char(255), SPACEKEY char(50), SENSITIVITY char(30), ORGANIZATION char(50), REPLCOST double, FontSize double, SECTIONKEY char(50), Shape.STLength() double,
      CharacterSpacing double, ON_CHANGEGEO smallint, Acres double, GROSS_SQUARE_FEET integer, PHYSICALCAPACITY integer, ASSIGNABLE char(10), ALLOCATIONPCT range_domain(dPercent:double:0:100), FACILITYNO smallint, FACILITYNAME char(255), BUILDINGKEY char(50), LeaseID char(50), FLOORCOUNT integer, URL char(1024), USABLE char(10), GROSSAREA double, Facnum char(50), CONSTRUCTION_TYPE char(5), last_edited_user char(255), ON_CHANGE smallint, LONGNAME char(100), BUDGETCODEID char(50), Shape_STArea_1 double, Size char(50), YOffset double, Shape_STLength_1 double, TITLE char(80), WordSpacing double, POIKEY integer, MAINTBY char(50), LINETYPE char(50),
      AnnotationClassID integer, FLOORID char(50), FilterWidth smallint, PrimaryFacnum char(253), ASSIGNMENTSUBCOLLEGEKEY char(5), CREATE_USER char(30)
    -> DYNAMIC (writer GEODATABASE_SDE_2)
    -> Water_Features (writer GEODATABASE_SDE_3)
DYNAMIC (writer GEODATABASE_SDE_2)
Water_Features (writer GEODATABASE_SDE_3)
    attributes: OBJECTID integer, Type char(50), SHAPE_STArea__ double, SHAPE_STLength__ double, MOD_USER char(30), OFM_LEASE_START_DATE date, CREATE_DATE date, TextString char(255), FACILITY_CODE char(4), OPERHOURSKEY char(50), SPACECAT1ID char(5), BUILDINGNAME char(50), Shape_STLength_12 double, SPACETYPECAT1KEY char(5), created_date date, Phase char(100), OrganizationSubCollegeID char(5), BUILDINGCONDITIONID char(50), TELEPHONEEXT char(25), NAME char(255), ATTACHMENTID integer, SurfaceLine char(50), created_user char(255), ORGANIZATIONKEY char(50), OFM_SITE_CODE char(3), FLOORPAGETEMPLATE char(3), ProjectNameWithoutNumber char(255), BUDGETCODEKEY char(50), FIRSTNAME char(255), ACCESSTYPEKEY char(50),
      ORGASSIGNABLE char(5), FLOORCODE char(5), Bldg_Key integer, Description char(255), VERTORDER smallint, OCCUPANCY smallint, SymbolID integer, LOGINID char(50), SHIFT char(50), FUNCTIONALUSEKEY char(50), last_edited_date date, BUILDINGTYPE char(50), OFM_CITY_CODE char(4), OFM_HSR char(3), FACILITY_NUMBER smallint, LASTEDITOR char(30), Notes char(300), Shape_STArea__ double, ROTATION double, BUILDINGCONDITION char(50), ASSIGNMENTKEY char(50), ADA char(15), SiteName char(50), FilterChangeDate date, CEOID integer, HorizontalAlignment smallint, ROOMNUMBER char(25), COSTCTR double, ModRotation range_domain(dEvac_ModRotation:double:0:360), FilterDepth smallint,
      SPACESTANDARD char(50), MOD_DATE date, CALCROT double, CONTENT_TYPE char(150), NOTES char(255), OFM_REPLACEMENT_COST_FACTOR integer, FilterQty smallint, SOURCEID char(30), FACNUM char(50), FLOORKEY char(50), OrganizationCollegeID char(3), COMMENTS char(255), ACCESSTYPE char(50), AssetRotation double, PathType char(50), SECTOR char(3), FACILITY_TYPE char(4), PERCENTASSIGNABLE double, EvacMap char(5), FIELDNAME char(64), FLOORSHORTNAME char(50), USABLEAREA double, ENTITYTYPEID char(50), Override integer, VACANCY smallint, DESCRIPTION char(255), GROUNDOFFSET double, OWNEDBY char(50), Scope char(2048), ASSIGNMENTCOUNT integer,
      EMPLOYEEID char(50), FilterLength smallint, ROOF char(10), OFM_LEGISLATIVE_DISTRICT char(2), EgressRotation range_domain(dEvac_ModRotation:double:0:360), GROUNDELEV double, DATA_SIZE integer, LONG_NAME char(100), OS_USER char(30), DEPARTMENT char(50), FloorID char(50), INTERIORSPACE char(3), KNOWNAS char(255), BUILDINGID char(50), TABLENAME char(254), LOGINKEY char(50), FSOID integer, PHOTOFILE char(100), FLOORPLANLINE char(3), Angle double, OFM_COUNTY_CODE char(3), SHORTNAME char(25), LNAMEFNAME char(140), SPACEUSECAT1KEY char(5), ASSIGNABLEAREA double, OFM_SITE_ADDRESS char(40), VACANCYRATE double, CharacterWidth double, STATUS char(3), FLOORAREA double,
      BUDGETCODE char(50), FlipAngle double, SPACEUSECAT2KEY char(5), FACILITYID char(50), CONDITIONKEY char(50), FUNCTIONALUSEID char(50), FontLeading double, FLOORLONGNAME char(100), FloorKey char(60), ADDRESS char(255), CM char(100), REGISTERED_HISTORIC_SITE char(1), MapFloorID char(50), SiteID char(50), TYPE char(20), Shape_STArea_12 double, FLOORLEVEL integer, ATT_NAME char(250), DDPEvacRot double, Name char(50), Italic smallint, DEFINITION char(256), CENTER_FACILITY_LONGITUDE double, Bold smallint, CEILINGHEIGHT double, SITEKEY smallint, Display char(50), SPACECAT2ID char(5), Status char(20), ENTITYKEY char(50),
      Comment char(255), CollegeName char(50), DepartmentName char(50), PubliclyAvailable char(5), SPACECAT1KEY char(5), VALUEINFO char(254), ORGANIZATIONID char(50), DisplayType char(50), DDPFLOORSORT char(71), FACILITYKEY char(50), CoordinateSystem smallint, VerticalAlignment smallint, SCHELEV integer, BUILDINGMANAGER char(50), ON_MANUAL smallint, PM char(2048), CENTER_FACILITY_LATITUDE double, BUILDINGS smallint, YEAR_CONSTRUCTED char(4), OutlineType char(25), DRAWINGNAME char(100), DisplayName char(255), AVAILABILITY char(50), ZOrder integer, BUILDING char(3), Lot_Number char(50), EMPLOYEEKEY char(50), Apex smallint, SPACESTANDARDKEY char(50), ASSIGNMENTCOLLEGEKEY char(3),
      LAST_MAJOR_RENOVATION_COST integer, Site char(50), LABEL char(100), OCCUPANCYRATE double, XOffset double, EMAIL char(255), NETAREA double, DENSITY double, AGGREGATE_FACILITY_NUMBER smallint, OrganizationCollegeKey char(3), LEASED_OR_OWNED char(6), ACCESSTYPEID char(50), OFM_CONDITION char(1), SPACESTANDARDID char(50), OFM_LEASE_END_DATE date, VALUEMETHOD char(254), SPACETYPECAT2KEY char(5), BUILDINGTYPEID char(50), BuildingID char(60), SOURCEDWG char(60), SITE char(7), CITY char(100), STATE char(2), BUILDINGTYPEKEY char(50), CAPACITY integer, DATA blob, CONSTRUCTION_OR_PURCHASE_COST integer, Neighborhood char(50), AVERAGEAREA smallint, RUN_WEIGHT smallint,
      USERTYPE char(255), AssetType char(50), ON_CREATE smallint, FontName char(255), YEARBUILT smallint, PERCENTUSABLE double, Underline smallint, REL_OBJECTID integer, LAST_MAJOR_RENOVATION_DATE date, ASSIGNMENTSUBCOLLEGE char(50), SPACEID char(50), EAPID double, LASTUPDATE date, COMMENTTEXT char(255), OrganizationDepartmentID char(7), FUNCTIONALUSE char(50), WEB_PLAN char(1), FeatureID integer, ASSIGNMENTDEPARTMENTKEY char(7), SubCollegeName char(50), Rotation double, ProjectID char(100), LASTNAME char(255), SPACEKEY char(50), SENSITIVITY char(30), ORGANIZATION char(50), REPLCOST double, FontSize double, SECTIONKEY char(50), Shape_STLength__ double,
      CharacterSpacing double, ON_CHANGEGEO smallint, Acres double, GROSS_SQUARE_FEET integer, PHYSICALCAPACITY integer, ASSIGNABLE char(10), ALLOCATIONPCT range_domain(dPercent:double:0:100), FACILITYNO smallint, FACILITYNAME char(255), BUILDINGKEY char(50), LeaseID char(50), FLOORCOUNT integer, URL char(1024), USABLE char(10), GROSSAREA double, Facnum char(50), CONSTRUCTION_TYPE char(5), last_edited_user char(255), ON_CHANGE smallint, LONGNAME char(100), BUDGETCODEID char(50), Shape_STArea_1 double, Size char(50), YOffset double, Shape_STLength_1 double, TITLE char(80), WordSpacing double, POIKEY integer, MAINTBY char(50), LINETYPE char(50),
      AnnotationClassID integer, FLOORID char(50), FilterWidth smallint, PrimaryFacnum char(253), ASSIGNMENTSUBCOLLEGEKEY char(5), CREATE_USER char(30)
