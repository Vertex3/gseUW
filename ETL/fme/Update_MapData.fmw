FME workspace Update_MapData.fmw

Readers:
- GEODATABASE_SDE_1: GEODATABASE_SDE
- GEODATABASE_SDE_2: GEODATABASE_SDE
- GEODATABASE_SDE_3: GEODATABASE_SDE

Writers:
- GEODATABASE_SDE_4: GEODATABASE_SDE
- GEODATABASE_SDE_6: GEODATABASE_SDE

Bookmark: New Bookmark
DBO.FloorplanLine (reader GEODATABASE_SDE_1)
    attributes: OBJECTID integer, SITEID char(60), BUILDINGID char(60), FLOORCODE char(20), FLOORID char(60), SOURCELAYER char(24), SOURCEID char(30), SOURCEDWG char(60), LASTUPDATE date, LASTEDITOR char(30), SHAPE.STLength() double
    -> AttributeRenamer_14
    -> HullAccumulator
AttributeRenamer_14
    ATTR_TABLE:
      RENAME_SET_DEFAULT BUILDINGID > BUILDINGKEY
      RENAME_SET_DEFAULT FLOORID > FLOORKEY
      RENAME_SET_DEFAULT SOURCELAYER > LINETYPE
      RENAME_SET_DEFAULT LASTEDITOR > last_edited_user
      RENAME_SET_DEFAULT LASTUPDATE > last_edited_date
    -> senstivity_filter_5
    -> DBO.FloorplanLine_ALL (writer GEODATABASE_SDE_4)
senstivity_filter_5: Tester
    TEST_MODE = Automatic
    TEST_CLAUSE:
      TEST @Value(BUILDINGKEY) = 1212
      TEST @Value(BUILDINGKEY) = 1053
      TEST @Value(BUILDINGKEY) = 6327
      TEST @Value(BUILDINGKEY) = 6403
    TEST_DESCRIPTION = ""
    BOOL_OP = OR
    FAILED -> DBO.FloorplanLine (writer GEODATABASE_SDE_4)
DBO.FloorplanLine (writer GEODATABASE_SDE_4)
    attributes: BUILDINGKEY char(50), FLOORKEY char(50), FLOORCODE char(5), LINETYPE char(50), created_user char(255), created_date date, last_edited_user char(255), last_edited_date date, SHAPE.STLength() double, OBJECTID integer
DBO.FloorplanLine_ALL (writer GEODATABASE_SDE_4)
    attributes: OBJECTID integer, BUILDINGKEY char(50), FLOORKEY char(50), FLOORCODE char(5), LINETYPE char(50), created_user char(255), created_date date, last_edited_user char(255), last_edited_date date, SHAPE.STLength() double

Bookmark: New Bookmark
HullAccumulator
    GROUP_BY = FLOORID
    HULLTYPE_PARAM = Convex ()
    3DMODE_PARAM = 2D
    HULL -> FeatureMerger_13 [REQUESTOR]
DBO.Floor_Table (reader GEODATABASE_SDE_1)
    attributes: OBJECTID integer, FLOORID char(60), BUILDINGID char(60), SITEID char(60), FLOORCODE char(20), SOURCEDWG char(100), SCHELEV integer, GROUNDOFFSET double, CALCROT double, LOCALROT double
    -> AttributeRemover_2
AttributeRemover_2
    REMOVE_ATTRS = SITEID,CALCROT,LOCALROT,OBJECTID
    -> AttributeRenamer_8
AttributeRenamer_8
    ATTR_TABLE = RENAME_SET_DEFAULT BUILDINGID > BUILDINGKEY
    -> DBO.Floor_Table (writer GEODATABASE_SDE_4)
    -> AttributeRenamer_5
    -> FeatureMerger_7 [REQUESTOR]
AttributeRenamer_5
    ATTR_TABLE:
      RENAME_SET_DEFAULT FLOORID > FT.FLOORID
      RENAME_SET_DEFAULT BUILDINGKEY > FT.BUILDINGID
    -> FeatureMerger_4 [SUPPLIER]
    -> FeatureMerger_3 [REQUESTOR]
    -> FeatureMerger_6 [SUPPLIER]
DBO.Floor_Table (writer GEODATABASE_SDE_4)
    attributes: BUILDINGKEY char(50), FLOORID char(50), FLOORCODE char(5), SOURCEDWG char(100), SCHELEV integer, GROUNDOFFSET double, OBJECTID integer
DBO.Floor_Level (reader GEODATABASE_SDE_1)
    attributes: OBJECTID integer, SITEID char(60), FLOORCODE char(20), FLOORLEVEL integer, NAMELONG char(100), NAMESHORT char(50)
    -> AttributeRemover_3
AttributeRemover_3
    REMOVE_ATTRS = SITEID,OBJECTID
    -> AttributeRenamer_10
AttributeRenamer_10
    ATTR_TABLE:
      RENAME_SET_DEFAULT NAMESHORT > FLOORSHORTNAME
      RENAME_SET_DEFAULT NAMELONG > FLOORLONGNAME
    -> DBO.Floor_Level (writer GEODATABASE_SDE_4)
    -> FeatureMerger_5 [SUPPLIER]
    -> FeatureMerger_8 [SUPPLIER]
DBO.Floor_Level (writer GEODATABASE_SDE_4)
    attributes: FLOORCODE char(5), FLOORLEVEL integer, FLOORSHORTNAME char(50), FLOORLONGNAME char(100), OBJECTID integer
DBO.FloorPageTemplate (reader GEODATABASE_SDE_1)
    attributes: OBJECTID integer, SITEID char(60), BUILDINGID char(60), CALCROT double, LOCALROT double, SOURCEID char(30), SOURCEDWG char(60), LASTUPDATE date, LASTEDITOR char(30), SHAPE.STArea() double, SHAPE.STLength() double
    -> AttributeRemover_4
AttributeRemover_4
    REMOVE_ATTRS = SHAPE.STLength(),SITEID,SHAPE.STArea(),LOCALROT,OBJECTID
    -> AttributeRenamer_22
AttributeRenamer_22
    ATTR_TABLE:
      RENAME_SET_DEFAULT BUILDINGID > BUILDINGKEY
      RENAME_SET_DEFAULT CALCROT > ROTATION
      RENAME_SET_DEFAULT LASTEDITOR > last_edited_user
      RENAME_SET_DEFAULT LASTUPDATE > last_edited_date
    -> FeatureMerger_7 [SUPPLIER]
    -> DBO.FloorPageTemplate (writer GEODATABASE_SDE_4)
    -> FeatureMerger_10 [SUPPLIER]
FeatureMerger_7
    ATTR_ACCUM_MODE = Merge Supplier
    JOIN_KEYS = @Value(BUILDINGKEY) @Value(BUILDINGKEY) AUTO
    SUPPLIERS_FIRST = No
    CONNECT_Z_MODE = First Wins
    PROCESS_DUPS = Yes
    MERGE_TYPE = Attributes and Geometry
    GEOM_TYPE = Build Polygons
    ATTR_CONFLICT_RES = Use Requestor
    IGNORE_NULLS = No
    MERGED -> FeatureMerger_8 [REQUESTOR]
FeatureMerger_8
    ATTR_ACCUM_MODE = Merge Supplier
    JOIN_KEYS = @Value(FLOORCODE) @Value(FLOORCODE) AUTO
    SUPPLIERS_FIRST = No
    PROCESS_DUPS = No
    MERGE_TYPE = Attributes Only
    ATTR_CONFLICT_RES = Use Requestor
    IGNORE_NULLS = No
    MERGED -> FeatureMerger_9 [REQUESTOR]
DBO.FloorPageTemplate (writer GEODATABASE_SDE_4)
    attributes: BUILDINGKEY char(50), ROTATION double, SOURCEID char(30), SOURCEDWG char(60), last_edited_date date, last_edited_user char(255), OBJECTID integer, SHAPE.STArea() double, SHAPE.STLength() double
dbo.FACILITY_VIEW (reader GEODATABASE_SDE_3)
    attributes: SITE_DESCRIPTION char(36), FACILITY_NUMBER smallint, FACILITY_CODE char(4), NAME char(20), LONG_NAME char(100), FACILITY_TYPE_DESCRIPTION char(36), STATUS_DESCRIPTION char(30), LEASED_OR_OWNED char(6), GROSS_SQUARE_FEET integer, UsableSqft integer, AssignableSqft integer, FloorCount integer, RoomCount integer, Capacity integer, PrimaryRoomTypeGroup char(25), PrimaryRoomTypeGroupSqft integer, PrimaryUnit char(30), PrimaryUnitSqft double, PrimaryDept char(30), PrimaryDeptSqft double, YEAR_CONSTRUCTED char(4), SECTOR char(3), CONSTRUCTION_OR_PURCHASE_COST integer, LAST_MAJOR_RENOVATION_DATE date, LAST_MAJOR_RENOVATION_COST integer, REGISTERED_HISTORIC_SITE char(1), CONSTRUCTION_TYPE char(5), AGGREGATE_FACILITY_NUMBER smallint, OFM_CONDITION char(1), PrimaryStreetAddress char(104),
      CITY char(25), STATE char(20), POSTCODE char(10), COUNTY char(25), COUNTRY char(30), COUNTRY_CODE_2 char(3), CENTER_FACILITY_LATITUDE double, CENTER_FACILITY_LONGITUDE double, Depts char(2147483647)
    -> FeatureMerger_2 [SUPPLIER]
    -> FeatureMerger_9 [SUPPLIER]
FeatureMerger_9
    ATTR_ACCUM_MODE = Merge Supplier
    JOIN_KEYS = @Value(BUILDINGKEY) @Value(FACILITY_NUMBER) AUTO
    SUPPLIERS_FIRST = No
    PROCESS_DUPS = No
    MERGE_TYPE = Attributes Only
    ATTR_CONFLICT_RES = Use Requestor
    IGNORE_NULLS = No
    MERGED -> AttributeRenamer_21
AttributeRenamer_21
    ATTR_TABLE:
      RENAME_SET_DEFAULT BUILDINGID > BUILDINGKEY
      RENAME_SET_DEFAULT NAMESHORT > FLOORSHORTNAME
      RENAME_SET_DEFAULT NAMELONG > FLOORLONGNAME
      RENAME_SET_DEFAULT CALCROT > ROTATION
      RENAME_SET_DEFAULT LASTEDITOR > last_edited_user
      RENAME_SET_DEFAULT LASTUPDATE > last_edited_date
      RENAME_SET_DEFAULT NAME > BUILDINGNAME
    -> AttributeCreator_7
AttributeCreator_7
    ATTR_TABLE = SET_TO DDPFLOORSORT = @Value(BUILDINGKEY)_@Value(FLOORLEVEL)
    -> senstivity_filter_3
    -> DBO.FloorPage_ALL (writer GEODATABASE_SDE_4)
    -> FeatureMerger_13 [SUPPLIER]
FeatureMerger_13
    REJECT_NULL_MISSING_KEYS = No
    ATTR_ACCUM_MODE = Merge Supplier
    JOIN_KEYS = @Value(FLOORID) @Value(FLOORID) AUTO
    SUPPLIERS_FIRST = No
    PROCESS_DUPS = No
    MERGE_TYPE = Attributes Only
    ATTR_CONFLICT_RES = Use Requestor
    IGNORE_NULLS = No
    MERGED -> senstivity_filter_6
    MERGED -> DBO.FloorPage_Wrapper_ALL (writer GEODATABASE_SDE_4)
DBO.FloorPage_Wrapper_ALL (writer GEODATABASE_SDE_4)
    attributes: FLOORID char(50), FLOORCODE char(5), BUILDINGKEY char(50), FLOORSHORTNAME char(50), FLOORLONGNAME char(100), BUILDINGNAME char(50), ROTATION double, DDPFLOORSORT char(71), last_edited_date date, last_edited_user char(255)
senstivity_filter_6: Tester
    TEST_MODE = Automatic
    TEST_CLAUSE:
      TEST @Value(BUILDINGKEY) = 1212
      TEST @Value(BUILDINGKEY) = 1053
      TEST @Value(BUILDINGKEY) = 6327
      TEST @Value(BUILDINGKEY) = 6403
    TEST_DESCRIPTION = ""
    BOOL_OP = OR
    PASSED -> DBO.FloorPage_Wrapper (writer GEODATABASE_SDE_4)
DBO.FloorPage_Wrapper (writer GEODATABASE_SDE_4)
    attributes: FLOORID char(50), FLOORCODE char(5), BUILDINGKEY char(50), FLOORSHORTNAME char(50), FLOORLONGNAME char(100), BUILDINGNAME char(50), ROTATION double, DDPFLOORSORT char(71), last_edited_date date, last_edited_user char(255)
DBO.FloorPage_ALL (writer GEODATABASE_SDE_4)
    attributes: OBJECTID integer, FLOORID char(50), FLOORCODE char(5), BUILDINGKEY char(50), FLOORSHORTNAME char(50), FLOORLONGNAME char(100), BUILDINGNAME char(50), ROTATION double, DDPFLOORSORT char(71), last_edited_date date, last_edited_user char(255), SHAPE.STArea() double, SHAPE.STLength() double
senstivity_filter_3: Tester
    TEST_MODE = Automatic
    TEST_CLAUSE:
      TEST @Value(BUILDINGKEY) = 1212
      TEST @Value(BUILDINGKEY) = 1053
      TEST @Value(BUILDINGKEY) = 6327
      TEST @Value(BUILDINGKEY) = 6403
    TEST_DESCRIPTION = ""
    BOOL_OP = OR
    FAILED -> DBO.FloorPage (writer GEODATABASE_SDE_4)
DBO.FloorPage (writer GEODATABASE_SDE_4)
    attributes: FLOORID char(50), FLOORCODE char(5), BUILDINGKEY char(50), FLOORSHORTNAME char(50), FLOORLONGNAME char(100), BUILDINGNAME char(50), ROTATION double, DDPFLOORSORT char(71), last_edited_date date, last_edited_user char(255), OBJECTID integer, SHAPE.STArea() double, SHAPE.STLength() double
DBO.Building (reader GEODATABASE_SDE_2)
    attributes: OBJECTID integer, BUILDINGID char(50), FACILITY_CODE char(4), SHAPE.STArea() double, SHAPE.STLength() double, ADA char(15), ADDRESS char(120), ASSIGNMENTKEY char(50), BUILDINGTYPEKEY char(50), BUILDINGMANAGER char(50), CAPACITY smallint, CONDITIONKEY char(50), DESCRIPTION char(255), FACILITYKEY char(50), FACILITYNAME char(255), FLOORCOUNT integer, GROSSAREA double, LONGNAME char(100), MAINTBY char(50), NETAREA double, OCCUPANCY smallint, OPERHOURSKEY char(50), OWNEDBY char(50), REPLCOST double, SHORTNAME char(25), URL char(255), YEARBUILT smallint, USABLEAREA double, ASSIGNABLEAREA double, PERCENTUSABLE double,
      PERCENTASSIGNABLE double, OCCUPANCYRATE double, VACANCYRATE double, DENSITY double, created_date date, created_user char(255), last_edited_date date, last_edited_user char(255)
    -> FeatureMerger_2 [REQUESTOR]
    -> Generalizer_2
Generalizer_2
    PRESERVE = Yes
    TOLERANCE = .05
    ALG_TEXT = Douglas (Generalize)
    -> Aggregator_2
Aggregator_2
    AGGREGATE_TYPE = Homogeneous Collection (If Possible)
    SEP = ,
    MODE = Geometry - Assemble One Level
    GROUP_BY = BUILDINGID
    ACCUM_ATTRS_NAME = Yes
    ORDERED = No
    AGGREGATE -> AttributeRenamer_4
AttributeRenamer_4
    ATTR_TABLE = RENAME_SET_DEFAULT BUILDINGID > B.BUILDINGID
    -> AttributeRemover
AttributeRemover
    REMOVE_ATTRS = PrimaryRoomTypeGroupSqft,CONSTRUCTION_TYPE,CONSTRUCTION_OR_PURCHASE_COST,FloorCount,LAST_MAJOR_RENOVATION_COST,SHAPE.STArea(),SITE,OFM_CONDITION,REGISTERED_HISTORIC_SITE,CENTER_FACILITY_LATITUDE,FACILITY_TYPE_DESCRIPTION,LEASED_OR_OWNED,UsableSqft,Depts,PrimaryRoomTypeGroup,SECTOR,SHAPE.STLength(),SITE_DESCRIPTION,GROSS_SQUARE_FEET,STATE,AGGREGATE_FACILITY_NUMBER,FACILITY_NUMBER,PrimaryStreetAddress,OBJECTID,POSTCODE,FACILITY_CODE,RoomCount,LONG_NAME,OUTLINETYPE,CENTER_FACILITY_LONGITUDE,COUNTRY,STATUS_DESCRIPTION,AssignableSqft,LAST_MAJOR_RENOVATION_DATE,YEAR_CONSTRUCTED,CITY
    -> FeatureMerger_3 [SUPPLIER]
FeatureMerger_3
    ATTR_ACCUM_MODE = Merge Supplier
    JOIN_KEYS = @Value(FT.BUILDINGID) @Value(B.BUILDINGID) AUTO
    SUPPLIERS_FIRST = No
    CONNECT_Z_MODE = First Wins
    PROCESS_DUPS = Yes
    MERGE_TYPE = Attributes and Geometry
    GEOM_TYPE = Build Polygons
    ATTR_CONFLICT_RES = Use Supplier
    IGNORE_NULLS = No
    MERGED -> AttributeRenamer_18
AttributeRenamer_18
    ATTR_TABLE = RENAME_SET_DEFAULT FT.FLOORID > B.FLOORID
    -> FeatureMerger_6 [REQUESTOR]
FeatureMerger_6
    ATTR_ACCUM_MODE = Merge Supplier
    JOIN_KEYS = @Value(B.FLOORID) @Value(FT.FLOORID) AUTO
    SUPPLIERS_FIRST = No
    CONNECT_Z_MODE = First Wins
    PROCESS_DUPS = Yes
    MERGE_TYPE = Attributes Only
    GEOM_TYPE = Build Polygons
    ATTR_CONFLICT_RES = Use Requestor
    IGNORE_NULLS = No
    MERGED -> AttributeRenamer_19
AttributeRenamer_19
    ATTR_TABLE:
      RENAME_SET_DEFAULT B.FLOORID > FLOORID
      RENAME_SET_DEFAULT B.BUILDINGID > BUILDINGID
    -> Dissolver
FeatureMerger_2
    ATTR_ACCUM_MODE = Merge Supplier
    JOIN_KEYS = @Value(BUILDINGID) @Value(FACILITY_NUMBER) AUTO
    SUPPLIERS_FIRST = No
    PROCESS_DUPS = No
    MERGE_TYPE = Attributes Only
    ATTR_CONFLICT_RES = Use Requestor
    IGNORE_NULLS = No
    MERGED -> AttributeRenamer_2
AttributeRenamer_2
    ATTR_TABLE:
      RENAME_SET_DEFAULT LONG_NAME > LONGNAME
      RENAME_SET_DEFAULT NAME > SHORTNAME
      RENAME_SET_DEFAULT MOD_DATE > last_edited_date
      RENAME_SET_DEFAULT MOD_USER > last_edited_user
      RENAME_SET_DEFAULT CREATE_DATE > created_date
      RENAME_SET_DEFAULT CREATE_USER > created_user
      RENAME_SET_DEFAULT GROSS_SQUARE_FEET > GROSSAREA
      RENAME_SET_DEFAULT YEAR_CONSTRUCTED > YEARBUILT
      RENAME_SET_DEFAULT FloorCount > FLOORCOUNT
      RENAME_SET_DEFAULT OFM_CONDITION > CONDITIONKEY
      RENAME_SET_DEFAULT PrimaryStreetAddress > ADDRESS
      RENAME_SET_DEFAULT RoomCount > ROOMCOUNT
      RENAME_SET_DEFAULT Depts > DEPTS
      RENAME_SET_DEFAULT AssignableSqft > ASSIGNABLEAREA
      RENAME_SET_DEFAULT STATUS_DESCRIPTION > STATUS
      RENAME_SET_DEFAULT UsableSqft > USABLEAREA
    -> AttributeFilter
AttributeFilter
    ATTR_NAME = LEASED_OR_OWNED
    ATTR_VALUES = <EMPTY>,<MISSING>,<NULL>,<UNFILTERED>,OWNED
    <EMPTY> -> DBO.Building
    <MISSING> -> DBO.Building
    <NULL> -> DBO.Building
    <UNFILTERED> -> DBO.Building
    OWNED -> AttributeCreator_4
AttributeCreator_4
    ATTR_TABLE = SET_TO OWNEDBY = UW
    -> DBO.Building
DBO.Building: Junction
    -> DBO.Building (writer GEODATABASE_SDE_6)
DBO.Building (writer GEODATABASE_SDE_6)
    attributes: BUILDINGID char(50), FACILITY_CODE char(4), ADA char(15), ADDRESS char(120), ASSIGNMENTKEY char(50), BUILDINGTYPEKEY char(50), BUILDINGMANAGER char(50), CAPACITY smallint, CONDITIONKEY char(50), DESCRIPTION char(255), FACILITYKEY char(50), FACILITYNAME char(255), FLOORCOUNT integer, GROSSAREA double, LONGNAME char(100), MAINTBY char(50), NETAREA double, OCCUPANCY smallint, OPERHOURSKEY char(50), OWNEDBY char(50), REPLCOST double, SHORTNAME char(25), URL char(255), YEARBUILT smallint, USABLEAREA double, ASSIGNABLEAREA double, PERCENTUSABLE double, PERCENTASSIGNABLE double, OCCUPANCYRATE double, VACANCYRATE double,
      DENSITY double, created_date date, created_user char(255), last_edited_date date, last_edited_user char(255), SHAPE.STArea() double, SHAPE.STLength() double
DBO.FloorArea (reader GEODATABASE_SDE_1)
    attributes: OBJECTID integer, SITEID char(60), BUILDINGID char(60), FLOORCODE char(20), FLOORID char(60), FLOORAREA double, SOURCEDWG char(60), LASTUPDATE date, LASTEDITOR char(30), SHAPE.STArea() double, SHAPE.STLength() double
    -> AttributeRenamer_7
    -> AttributeRenamer_6
AttributeRenamer_7
    ATTR_TABLE = RENAME_SET_DEFAULT BUILDINGID > BUILDINGKEY
    -> senstivity_filter_4
    -> DBO.FloorArea_ALL (writer GEODATABASE_SDE_4)
DBO.FloorArea_ALL (writer GEODATABASE_SDE_4)
    attributes: OBJECTID integer, BUILDINGKEY char(50), FLOORID char(50), FLOORCODE char(5), FLOORAREA double, SOURCEDWG char(60), LASTUPDATE date, LASTEDITOR char(30), SHAPE.STArea() double, SHAPE.STLength() double
senstivity_filter_4: Tester
    TEST_MODE = Automatic
    TEST_CLAUSE:
      TEST @Value(BUILDINGKEY) = 1212
      TEST @Value(BUILDINGKEY) = 1053
      TEST @Value(BUILDINGKEY) = 6327
      TEST @Value(BUILDINGKEY) = 6403
    TEST_DESCRIPTION = ""
    BOOL_OP = OR
    FAILED -> DBO.FloorArea (writer GEODATABASE_SDE_4)
DBO.FloorArea (writer GEODATABASE_SDE_4)
    attributes: BUILDINGKEY char(50), FLOORID char(50), FLOORCODE char(5), FLOORAREA double, SOURCEDWG char(60), LASTUPDATE date, LASTEDITOR char(30), SHAPE.STArea() double, SHAPE.STLength() double, OBJECTID integer
AttributeRenamer_6
    ATTR_TABLE = RENAME_SET_DEFAULT FLOORID > FA.FLOORID
    -> FeatureMerger_4 [REQUESTOR]
FeatureMerger_4
    ATTR_ACCUM_MODE = Merge Supplier
    JOIN_KEYS = @Value(FA.FLOORID) @Value(FT.FLOORID) AUTO
    SUPPLIERS_FIRST = No
    PROCESS_DUPS = No
    MERGE_TYPE = Attributes Only
    ATTR_CONFLICT_RES = Use Requestor
    IGNORE_NULLS = No
    MERGED -> AttributeRenamer_20
AttributeRenamer_20
    ATTR_TABLE = RENAME_SET_DEFAULT FA.FLOORID > FLOORID
    -> Dissolver_2
Dissolver_2
    GROUP_BY = FLOORID
    ACCUM_INPUT_ATTRS = Merge Incoming Attributes
    CONNECT_Z_MODE = Ignore
    NO_OVRLP = No
    AREA -> Aggregator_3
Aggregator_3
    AGGREGATE_TYPE = Homogeneous Collection (If Possible)
    SEP = ,
    MODE = Geometry - Assemble One Level
    GROUP_BY = FLOORID
    ACCUM_ATTRS_NAME = Get Attributes From One Representative Feature
    ORDERED = No
    AGGREGATE -> Dissolver
Dissolver
    GROUP_BY = FLOORID
    ACCUM_INPUT_ATTRS = Yes
    CONNECT_Z_MODE = First Wins
    NO_OVRLP = No
    AREA -> Tester_2
Tester_2
    TEST_MODE = Automatic
    TEST_CLAUSE = TEST @Value(FLOORCODE) ATTRIBUTE_HAS_VALUE ""
    TEST_DESCRIPTION = ""
    BOOL_OP = OR
    PASSED -> Aggregator
Aggregator
    AGGREGATE_TYPE = Homogeneous Collection (If Possible)
    SEP = ,
    MODE = Geometry - Assemble One Level
    GROUP_BY = FLOORID
    ACCUM_ATTRS_NAME = Yes
    ORDERED = No
    AGGREGATE -> GeometryValidator
GeometryValidator
    CONNECT_Z_MODE_SI = First Wins
    REPAIR = Yes
    CONNECT_Z_MODE_TR = First Wins
    ARC_ENDPOINT_TOLERANCE_MODE = Auto
    SELF_INTERSECTING = SELF_INTERSECTING
    CHECK_HOLE_TOUCHING_POLYGON = No
    PRESETS = Custom
    CONSECUTIVE_IDENTICAL_VERTICES_2D = CONSECUTIVE_IDENTICAL_VERTICES_2D
    NULL_REMOVAL = NULL_REMOVAL
    DUP_COORDS_CHECK_Z = Yes
    TYPE_REPAIR = TYPE_REPAIR
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    SUMMARY = Detailed
    ISSUE_ATTR_NAME = _issues
    PASSED -> FeatureMerger_5 [REQUESTOR]
    REPAIRED -> FeatureMerger_5 [REQUESTOR]
FeatureMerger_5
    ATTR_ACCUM_MODE = Merge Supplier
    JOIN_KEYS = @Value(FLOORCODE) @Value(FLOORCODE) AUTO
    SUPPLIERS_FIRST = No
    PROCESS_DUPS = No
    MERGE_TYPE = Attributes Only
    ATTR_CONFLICT_RES = Use Requestor
    IGNORE_NULLS = No
    MERGED -> FeatureMerger_10 [REQUESTOR]
FeatureMerger_10
    ATTR_ACCUM_MODE = Merge Supplier
    JOIN_KEYS = @Value(BUILDINGID) @Value(BUILDINGKEY) AUTO
    SUPPLIERS_FIRST = No
    PROCESS_DUPS = No
    MERGE_TYPE = Attributes Only
    ATTR_CONFLICT_RES = Use Requestor
    IGNORE_NULLS = No
    MERGED -> FeatureMerger_11 [REQUESTOR]
dbo.Floor (reader GEODATABASE_SDE_1)
    attributes: OBJECTID integer, FLOORID char(60), FLOORCODE char(20), NAMESHORT char(50), NAMELONG char(100), INTERIORSPACE char(3), FLOORPLANLINE char(3), FLOORAREA char(3), SCHELEV integer, GROUNDELEV double, FLOORLEVEL integer, STACKLEVEL double, SENSITIVITY char(30), DRAWINGNAME char(100), BUILDINGID char(60), BLDGNAME char(30), CALCROT double, LOCALROT double, DDPFLOORSORT char(71)
    -> AttributeRemover_5
AttributeRemover_5
    REMOVE_ATTRS = SCHELEV,NAMELONG,BLDGNAME,FLOORCODE,SENSITIVITY,DRAWINGNAME,CALCROT,DDPFLOORSORT,FLOORPLANLINE,FLOORLEVEL,LOCALROT,OBJECTID,BUILDINGID,INTERIORSPACE,GROUNDELEV,NAMESHORT,FLOORAREA
    -> FeatureMerger_11 [SUPPLIER]
FeatureMerger_11
    ATTR_ACCUM_MODE = Merge Supplier
    JOIN_KEYS = @Value(FLOORID) @Value(FLOORID) AUTO
    SUPPLIERS_FIRST = No
    PROCESS_DUPS = No
    MERGE_TYPE = Attributes Only
    ATTR_CONFLICT_RES = Use Requestor
    IGNORE_NULLS = No
    MERGED -> AttributeRenamer_9
AttributeRenamer_9
    ATTR_TABLE:
      RENAME_SET_DEFAULT BUILDINGID > BUILDINGKEY
      RENAME_SET_DEFAULT FLOORAREA > GROSSAREA
      RENAME_SET_DEFAULT NAME > BUILDINGNAME
      RENAME_SET_DEFAULT UsableSqft > USABLEAREA
      RENAME_SET_DEFAULT AssignableSqft > ASSIGNABLEAREA
      RENAME_SET_DEFAULT FT.FLOORID > FLOORID
      RENAME_SET_DEFAULT STACKLEVEL > VERTORDER
    -> AttributeCreator_6
AttributeCreator_6
    ATTR_TABLE = SET_TO DDPFLOORSORT = @Value(FT.BUILDINGID)_@Value(FLOORLEVEL)
    -> DBO.Floor (writer GEODATABASE_SDE_4)
DBO.Floor (writer GEODATABASE_SDE_4)
    attributes: FLOORID char(50), BUILDINGKEY char(50), BUILDINGNAME char(50), FLOORSHORTNAME char(50), FLOORLONGNAME char(100), FLOORCODE char(5), GROSSAREA double, NETAREA double, ROTATION double, VERTORDER smallint, DDPFLOORSORT char(71), USABLEAREA double, ASSIGNABLEAREA double, PERCENTUSABLE double, PERCENTASSIGNABLE double, ROOF char(10), created_date date, created_user char(255), last_edited_date date, last_edited_user char(255), SHAPE.STArea() double, SHAPE.STLength() double, OBJECTID integer

Bookmark: New Bookmark
DBO.InteriorSpace (reader GEODATABASE_SDE_1)
    attributes: OBJECTID integer, SITEID char(60), BUILDINGID char(60), FLOORCODE char(20), FLOORID char(60), ROOMNUMBER char(30), SPACEID char(60), SPACECLASS char(60), SPACEAREA double, SOURCEID char(30), SOURCEDWG char(60), LASTUPDATE date, LASTEDITOR char(30), SHAPE.STArea() double, SHAPE.STLength() double
    -> FeatureMerger [REQUESTOR]
dbo.ROOM (reader GEODATABASE_SDE_3)
    attributes: FACILITY_NUMBER smallint, FACILITY_CODE char(4), FLOOR_CODE char(4), ROOM_NUMBER char(20), SQUARE_FEET integer, ROOM_TYPE char(3), ORGANIZATION char(10), DESCRIPTION char(50), CAPACITY smallint, SURGE_SPACE char(1), LEASED_TO_EXTERNAL char(1), NEEDS_REASSIGNMENT char(1), EXTERIOR_WINDOW char(1), ASSIGNOR char(4), UNDERGRADS char(2), GRADS char(2), VISITING_PROFS char(2), SHARED char(1), ROOM_ASSIGN_COUNT smallint, NOTES char(256), FACROOM char(30), FLOOR_PLAN char(1), CONFIRM_USER char(30), CONFIRM_DATE date, CREATE_USER char(30), CREATE_DATE date, MOD_USER char(30), MOD_DATE date, OS_USER char(30), MOD_NETID char(30),
      MOD_NETID_DATE date
    -> AttributeCreator_3
AttributeCreator_3
    ATTR_TABLE = SET_TO SPACEID = @Value(FACILITY_NUMBER)_@Value(FLOOR_CODE)_@Value(ROOM_NUMBER)
    -> FeatureMerger [SUPPLIER]
FeatureMerger
    ATTR_ACCUM_MODE = Merge Supplier
    JOIN_KEYS = @Value(SPACEID) @Value(SPACEID) AUTO
    SUPPLIERS_FIRST = No
    PROCESS_DUPS = No
    MERGE_TYPE = Attributes Only
    ATTR_CONFLICT_RES = Use Requestor
    IGNORE_NULLS = No
    MERGED -> AttributeRenamer
    NOT_MERGED -> AttributeRenamer
AttributeRenamer
    ATTR_TABLE:
      RENAME_SET_DEFAULT SPACEAREA > NETAREA
      RENAME_SET_DEFAULT FLOORID > FLOORKEY
      RENAME_SET_DEFAULT BUILDINGID > BUILDINGKEY
      RENAME_SET_DEFAULT MOD_NETID > last_edited_user
      RENAME_SET_DEFAULT MOD_NETID_DATE > last_edited_date
      RENAME_SET_DEFAULT ORGANIZATION > ASSIGNMENTKEY
      RENAME_SET_DEFAULT CREATE_DATE > created_date
      RENAME_SET_DEFAULT CREATE_USER > created_user
      RENAME_SET_DEFAULT ORGANIZATION > ASSIGNMENTKEY
      RENAME_SET_DEFAULT ROOM_TYPE > SPACETYPECAT2KEY
    -> AttributeCreator_8
AttributeCreator_8
    ATTR_TABLE:
      SET_TO ASSIGNMENTCOLLEGEKEY = @Left(@Value(ASSIGNMENTKEY),3)
      SET_TO ASSIGNMENTDEPARTMENTKEY = @Left(@Value(ASSIGNMENTKEY),7)
      SET_TO ASSIGNMENTSUBCOLLEGEKEY = @Left(@Value(ASSIGNMENTKEY),5)
    -> TestFilter
TestFilter
    DEFAULT_VALUE = <UNFILTERED>
    TEST_LIST = BOOL_OP,OR,COMPOSITE_TEST,<Unused>,TEST_CLAUSE,"TEST @Value(SPACETYPECAT2KEY) <= 099",space type <= 099
    space type <= 099 -> AttributeCreator
    <UNFILTERED> -> AttributeCreator_2
AttributeCreator
    ATTR_TABLE:
      SET_TO ASSIGNABLE = No
      SET_TO ORGASSIGNABLE = No
    -> FeatureMerger_12 [REQUESTOR]
AttributeCreator_2
    ATTR_TABLE:
      SET_TO ASSIGNABLE = Yes
      SET_TO ORGASSIGNABLE = Yes
    -> FeatureMerger_12 [REQUESTOR]
dbo.ROOM_TYPE (reader GEODATABASE_SDE_3)
    attributes: ROOM_TYPE char(3), ROOM_TYPE_GROUP char(1), PRIMARY_USE char(20), SPACE_CATEGORY char(20), SCHOOL_OF_MEDICINE char(1), GENERAL char(1), HMC char(1), SECURITY_LEVEL char(1), REPLACEMENT_CODE char(3)
    -> AttributeRemover_8
AttributeRemover_8
    REMOVE_ATTRS = HMC,REPLACEMENT_CODE,SCHOOL_OF_MEDICINE,GENERAL,ROOM_TYPE_GROUP,SPACE_CATEGORY,SECURITY_LEVEL
    -> AttributeRenamer_3
AttributeRenamer_3
    ATTR_TABLE:
      RENAME_SET_DEFAULT ROOM_TYPE > SPACECAT2ID
      RENAME_SET_DEFAULT PRIMARY_USE > DESCRIPTION
    -> AttributeCreator_5
AttributeCreator_5
    ATTR_TABLE = SET_TO SPACECAT1KEY = @Left(@Value(SPACECAT2ID),1)00
    -> AttributeRemover_6
    -> Tester_3
Tester_3
    TEST_MODE = Automatic
    TEST_CLAUSE = TEST @Left(@Value(SPACECAT2ID),1) = 0
    TEST_DESCRIPTION = ""
    BOOL_OP = OR
    PASSED -> group_3
    FAILED -> DBO.SpaceClassificationLevel2 (writer GEODATABASE_SDE_4)
group_3: AttributeCreator
    ATTR_TABLE = SET_TO spacecatgroup = @Left(@Value(SPACECAT2ID),2)
    -> AttributeFilter_4
AttributeFilter_4
    ATTR_NAME = spacecatgroup
    ATTR_VALUES = <EMPTY>,<MISSING>,<NULL>,<UNFILTERED>,01,02,03,04,05,06,07,09
    01 -> Building_Service_2
    02 -> Circulation_2
    03 -> Mechanical_2
    04 -> Mechanical_2
    05 -> Unclassified_2
    06 -> Unclassified_2
    07 -> Unclassified_2
    09 -> Building_Service_2
Building_Service_2: AttributeCreator
    ATTR_TABLE = SET_TO SPACECAT1KEY = 010
    -> Building_Service_2_OUTPUT
Circulation_2: AttributeCreator
    ATTR_TABLE = SET_TO SPACECAT1KEY = 020
    -> Building_Service_2_OUTPUT
Mechanical_2: AttributeCreator
    ATTR_TABLE = SET_TO SPACECAT1KEY = 030
    -> Building_Service_2_OUTPUT
Unclassified_2: AttributeCreator
    ATTR_TABLE = SET_TO SPACECAT1KEY = 000
    -> Building_Service_2_OUTPUT
Building_Service_2_OUTPUT: Junction
    -> DBO.SpaceClassificationLevel2 (writer GEODATABASE_SDE_4)
DBO.SpaceClassificationLevel2 (writer GEODATABASE_SDE_4)
    attributes: SPACECAT2ID char(5), DESCRIPTION char(255), SPACECAT1KEY char(5), OBJECTID integer
AttributeRemover_6
    REMOVE_ATTRS = DESCRIPTION
    -> AttributeRenamer_23
AttributeRenamer_23
    ATTR_TABLE = RENAME_SET_DEFAULT SPACECAT1KEY > SPACECAT1ID
    -> Tester
Tester
    TEST_MODE = Automatic
    TEST_CLAUSE = TEST @Left(@Value(SPACECAT2ID),1) = 0
    TEST_DESCRIPTION = ""
    BOOL_OP = OR
    PASSED -> group_2
    FAILED -> group
group_2: AttributeCreator
    ATTR_TABLE = SET_TO spacecatgroup = @Left(@Value(SPACECAT2ID),2)
    -> AttributeFilter_2
AttributeFilter_2
    ATTR_NAME = spacecatgroup
    ATTR_VALUES = <EMPTY>,<MISSING>,<NULL>,<UNFILTERED>,01,02,03,04,05,06,07,09
    01 -> Building_Service
    02 -> Circulation
    03 -> Mechanical
    04 -> Mechanical
    05 -> Unclassified
    06 -> Unclassified
    07 -> Unclassified
    09 -> Building_Service
Building_Service: AttributeCreator
    ATTR_TABLE:
      SET_TO DESCRIPTION = Building Service
      SET_TO SPACECAT1ID = 010
    -> Non_Assignable
Circulation: AttributeCreator
    ATTR_TABLE:
      SET_TO DESCRIPTION = Circulation
      SET_TO SPACECAT1ID = 020
    -> Non_Assignable
Mechanical: AttributeCreator
    ATTR_TABLE:
      SET_TO DESCRIPTION = Mechanical
      SET_TO SPACECAT1ID = 030
    -> Non_Assignable
Non_Assignable: AttributeCreator
    ATTR_TABLE = SET_TO ORGASSIGNABLE = No
    -> Non_Assignable_OUTPUT
    -> DuplicateFilter_4
Unclassified: AttributeCreator
    ATTR_TABLE:
      SET_TO DESCRIPTION = Building Service
      SET_TO SPACECAT1ID = 000
    -> Assignable
group: AttributeCreator
    ATTR_TABLE = SET_TO spacecatgroup = @Left(@Value(SPACECAT2ID),1)
    -> AttributeFilter_3
AttributeFilter_3
    ATTR_NAME = spacecatgroup
    ATTR_VALUES = <EMPTY>,<MISSING>,<NULL>,<UNFILTERED>,1,2,3,4,5,6,7,8,9
    1 -> Classroom
    2 -> Labs
    3 -> Office
    4 -> Study
    5 -> Special
    6 -> General
    7 -> Support
    8 -> Health_Care
    9 -> Residential
Classroom: AttributeCreator
    ATTR_TABLE = SET_TO DESCRIPTION = Classrooms
    -> Assignable
Labs: AttributeCreator
    ATTR_TABLE = SET_TO DESCRIPTION = Laboratory Facilities
    -> Assignable
Office: AttributeCreator
    ATTR_TABLE = SET_TO DESCRIPTION = Office Facilities
    -> Assignable
Study: AttributeCreator
    ATTR_TABLE = SET_TO DESCRIPTION = Study Facilities
    -> Assignable
Special: AttributeCreator
    ATTR_TABLE = SET_TO DESCRIPTION = Special Use Facilities
    -> Assignable
General: AttributeCreator
    ATTR_TABLE = SET_TO DESCRIPTION = General Use Faclities
    -> Assignable
Support: AttributeCreator
    ATTR_TABLE = SET_TO DESCRIPTION = Support Facilities
    -> Assignable
Health_Care: AttributeCreator
    ATTR_TABLE = SET_TO DESCRIPTION = Health Care Facilities
    -> Assignable
Residential: AttributeCreator
    ATTR_TABLE = SET_TO DESCRIPTION = Residential Facilities
    -> Assignable
Assignable: AttributeCreator
    ATTR_TABLE = SET_TO ORGASSIGNABLE = Yes
    -> DuplicateFilter_4
    -> Non_Assignable_OUTPUT
Non_Assignable_OUTPUT: Junction
    -> AttributeRenamer_24
AttributeRenamer_24
    ATTR_TABLE = RENAME_SET_DEFAULT SPACECAT1ID > SPACETYPECAT1KEY
    -> FeatureMerger_12 [SUPPLIER]
FeatureMerger_12
    REJECT_NULL_MISSING_KEYS = No
    ATTR_ACCUM_MODE = Merge Supplier
    JOIN_KEYS = @Value(SPACETYPECAT2KEY) @Value(SPACECAT2ID) AUTO
    SUPPLIERS_FIRST = No
    PROCESS_DUPS = No
    MERGE_TYPE = Attributes Only
    ATTR_CONFLICT_RES = Use Requestor
    IGNORE_NULLS = No
    MERGED -> SpaceCat1isNotNull
    NOT_MERGED -> SpaceCat1isNotNull
SpaceCat1isNotNull: Tester
    TEST_MODE = Automatic
    TEST_CLAUSE = TEST @Value(SPACETYPECAT1KEY) ATTRIBUTE_HAS_VALUE ""
    TEST_DESCRIPTION = ""
    BOOL_OP = OR
    PASSED -> OrgIsAssigned
    FAILED -> Space_Cat_to_590
Space_Cat_to_590: AttributeCreator
    ATTR_TABLE:
      SET_TO SPACETYPECAT2KEY = 590
      SET_TO SPACETYPECAT1KEY = 500
    -> OrgIsAssigned
OrgIsAssigned: Tester
    TEST_MODE = Automatic
    TEST_CLAUSE = TEST @Value(ASSIGNMENTKEY) ATTRIBUTE_HAS_VALUE ""
    TEST_DESCRIPTION = ""
    BOOL_OP = OR
    PASSED -> AttributeCreator_13_OUTPUT
    FAILED -> AttributeCreator_13
AttributeCreator_13
    ATTR_TABLE:
      SET_TO ASSIGNMENTKEY = UNKNOWN
      SET_TO ASSIGNMENTCOLLEGEKEY = UNK
      SET_TO ASSIGNMENTSUBCOLLEGEKEY = UNKNO
      SET_TO ASSIGNMENTDEPARTMENTKEY = UNKNOWN
    -> AttributeCreator_13_OUTPUT
AttributeCreator_13_OUTPUT: Junction
    -> CenterPointReplacer
    -> DBO.InteriorSpace_ALL (writer GEODATABASE_SDE_4)
    -> senstivity_filter
senstivity_filter: Tester
    TEST_MODE = Automatic
    TEST_CLAUSE:
      TEST @Value(BUILDINGKEY) = 1212
      TEST @Value(BUILDINGKEY) = 1053
      TEST @Value(BUILDINGKEY) = 6327
      TEST @Value(BUILDINGKEY) = 6403
    TEST_DESCRIPTION = ""
    BOOL_OP = OR
    FAILED -> DBO.InteriorSpace (writer GEODATABASE_SDE_4)
DBO.InteriorSpace (writer GEODATABASE_SDE_4)
    attributes: SPACEID char(50), ASSIGNMENTKEY char(50), CAPACITY integer, PHYSICALCAPACITY integer, DESCRIPTION char(255), FLOORKEY char(50), FLOORCODE char(5), GROSSAREA double, LONGNAME char(100), NETAREA double, SHORTNAME char(25), SPACETYPECAT1KEY char(5), SPACETYPECAT2KEY char(5), SPACEUSECAT1KEY char(5), SPACEUSECAT2KEY char(5), USABLE char(10), ASSIGNABLE char(10), ORGASSIGNABLE char(10), created_date date, created_user char(255), last_edited_date date, last_edited_user char(255), SHAPE.STArea() double, SHAPE.STLength() double, OBJECTID integer, ACCESSTYPEKEY char(50), ADA char(15), ALLOCATIONPCT double, CEILINGHEIGHT double, OCCUPANCY smallint,
      SECTIONKEY char(50), SPACESTANDARDKEY char(50), AVAILABILITY char(50), VACANCY smallint, ROOMNUMBER char(25), BUILDINGKEY char(50), ASSIGNMENTCOLLEGEKEY char(3), ASSIGNMENTDEPARTMENTKEY char(7), ASSIGNMENTSUBCOLLEGEKEY char(5)
DBO.InteriorSpace_ALL (writer GEODATABASE_SDE_4)
    attributes: OBJECTID integer, SPACEID char(50), ALLOCATIONPCT double, ASSIGNMENTKEY char(50), CAPACITY integer, PHYSICALCAPACITY integer, DESCRIPTION char(255), FLOORKEY char(50), FLOORCODE char(5), GROSSAREA double, LONGNAME char(100), SHORTNAME char(25), SPACETYPECAT1KEY char(5), SPACETYPECAT2KEY char(5), SPACEUSECAT1KEY char(5), SPACEUSECAT2KEY char(5), AVAILABILITY char(50), USABLE char(10), ASSIGNABLE char(10), ORGASSIGNABLE char(10), created_date date, created_user char(255), last_edited_date date, last_edited_user char(255), SHAPE.STArea() double, SHAPE.STLength() double, ROOMNUMBER char(25), ACCESSTYPEKEY char(50), ADA char(15), CEILINGHEIGHT double,
      NETAREA double, OCCUPANCY smallint, SECTIONKEY char(50), SPACESTANDARDKEY char(50), VACANCY smallint, BUILDINGKEY char(50), ASSIGNMENTCOLLEGEKEY char(3), ASSIGNMENTDEPARTMENTKEY char(7), ASSIGNMENTSUBCOLLEGEKEY char(5)
CenterPointReplacer
    MODE = Inside Point
    POINT -> senstivity_filter_2
    POINT -> DBO.InteriorSpace_Point_ALL (writer GEODATABASE_SDE_4)
DBO.InteriorSpace_Point_ALL (writer GEODATABASE_SDE_4)
    attributes: OBJECTID integer, SPACEID char(50), ALLOCATIONPCT double, ASSIGNMENTKEY char(50), CAPACITY integer, PHYSICALCAPACITY integer, DESCRIPTION char(255), FLOORKEY char(50), FLOORCODE char(5), GROSSAREA double, LONGNAME char(100), SHORTNAME char(25), SPACETYPECAT1KEY char(5), SPACETYPECAT2KEY char(5), SPACEUSECAT1KEY char(5), SPACEUSECAT2KEY char(5), AVAILABILITY char(50), USABLE char(10), ASSIGNABLE char(10), ORGASSIGNABLE char(10), created_date date, created_user char(255), last_edited_date date, last_edited_user char(255), ROOMNUMBER char(25), ACCESSTYPEKEY char(50), ADA char(15), CEILINGHEIGHT double, NETAREA double, OCCUPANCY smallint,
      SECTIONKEY char(50), SPACESTANDARDKEY char(50), VACANCY smallint, BUILDINGKEY char(50), ASSIGNMENTCOLLEGEKEY char(3), ASSIGNMENTDEPARTMENTKEY char(7), ASSIGNMENTSUBCOLLEGEKEY char(5)
senstivity_filter_2: Tester
    TEST_MODE = Automatic
    TEST_CLAUSE:
      TEST @Value(BUILDINGKEY) = 1212
      TEST @Value(BUILDINGKEY) = 1053
      TEST @Value(BUILDINGKEY) = 6327
      TEST @Value(BUILDINGKEY) = 6403
    TEST_DESCRIPTION = ""
    BOOL_OP = OR
    FAILED -> DBO.InteriorSpace_Point (writer GEODATABASE_SDE_4)
DBO.InteriorSpace_Point (writer GEODATABASE_SDE_4)
    attributes: OBJECTID integer, SPACEID char(50), ALLOCATIONPCT double, ASSIGNMENTKEY char(50), CAPACITY integer, PHYSICALCAPACITY integer, DESCRIPTION char(255), FLOORKEY char(50), FLOORCODE char(5), GROSSAREA double, LONGNAME char(100), SHORTNAME char(25), SPACETYPECAT1KEY char(5), SPACETYPECAT2KEY char(5), SPACEUSECAT1KEY char(5), SPACEUSECAT2KEY char(5), AVAILABILITY char(50), USABLE char(10), ASSIGNABLE char(10), ORGASSIGNABLE char(10), created_date date, created_user char(255), last_edited_date date, last_edited_user char(255), ROOMNUMBER char(25), ACCESSTYPEKEY char(50), ADA char(15), CEILINGHEIGHT double, NETAREA double, OCCUPANCY smallint,
      SECTIONKEY char(50), SPACESTANDARDKEY char(50), VACANCY smallint, BUILDINGKEY char(50), ASSIGNMENTCOLLEGEKEY char(3), ASSIGNMENTDEPARTMENTKEY char(7), ASSIGNMENTSUBCOLLEGEKEY char(5)
DuplicateFilter_4
    INPUT_ORDERED_CHOICE = No
    KEYATTR = SPACECAT1ID
    UNIQUE -> DBO.SpaceClassificationLevel1 (writer GEODATABASE_SDE_4)
DBO.SpaceClassificationLevel1 (writer GEODATABASE_SDE_4)
    attributes: SPACECAT1ID char(5), DESCRIPTION char(50), ORGASSIGNABLE char(5), OBJECTID integer
