FME workspace Update_newmapdata_new_cadsde.fmw

Readers:
- GEODATABASE_SDE_1: GEODATABASE_SDE
- GEODATABASE_SDE_2: GEODATABASE_SDE
- GEODATABASE_SDE_3: GEODATABASE_SDE

Writers:
- GEODATABASE_SDE_4: GEODATABASE_SDE
- GEODATABASE_SDE_5: GEODATABASE_SDE
- GEODATABASE_SDE_6: GEODATABASE_SDE
- GEODATABASE_SDE_7: GEODATABASE_SDE

Bookmark: New Bookmark
dbo.ORG_DEPT (reader GEODATABASE_SDE_3)
    attributes: ORG_DEPT char(7), ORG_DEPT_NAME char(30), ORG_SUBCOLLEGE char(5), ORG_SUBCOLLEGE_NAME char(30), ORG_COLLEGE char(3), ORG_COLLEGE_NAME char(30)
    -> Sorter
Sorter
    SORT_PARM = ORG_DEPT NUMERIC ASCENDING
    SORTED -> AttributeRenamer_25
AttributeRenamer_25
    ATTR_TABLE:
      RENAME_SET_DEFAULT ORG_COLLEGE > OrganizationCollegeID
      RENAME_SET_DEFAULT ORG_DEPT > OrganizationDepartmentID
      RENAME_SET_DEFAULT ORG_COLLEGE_NAME > CollegeName
      RENAME_SET_DEFAULT ORG_DEPT_NAME > DepartmentName
      RENAME_SET_DEFAULT ORG_SUBCOLLEGE > OrganizationSubCollegeID
      RENAME_SET_DEFAULT ORG_SUBCOLLEGE_NAME > SubCollegeName
    -> AttributeCreator_10
    -> AttributeRemover_7
    -> AttributeCreator_11
AttributeRemover_7
    REMOVE_ATTRS = OrganizationDepartmentID,DepartmentName
    -> DuplicateFilter_2
DuplicateFilter_2
    INPUT_ORDERED_CHOICE = Yes
    KEYATTR = OrganizationCollegeID
    UNIQUE -> DBO.OrganizationCollege (writer GEODATABASE_SDE_4)
    UNIQUE -> DBO.OrganizationCollege (writer GEODATABASE_SDE_5)
    UNIQUE -> DBO.OrganizationCollege (writer GEODATABASE_SDE_6)
DBO.OrganizationCollege (writer GEODATABASE_SDE_4)
    attributes: OrganizationCollegeID char(3), CollegeName char(50), OBJECTID integer
DBO.OrganizationCollege (writer GEODATABASE_SDE_5)
    attributes: OrganizationCollegeID char(3), CollegeName char(50), OBJECTID integer
DBO.OrganizationCollege (writer GEODATABASE_SDE_6)
    attributes: OrganizationCollegeID char(3), CollegeName char(50), OBJECTID integer
AttributeCreator_11
    ATTR_TABLE:
      SET_TO OrganizationSubCollegeKey = @Value(OrganizationSubCollegeID)
      SET_TO OrganizationCollegeKey = @Value(OrganizationCollegeID)
    -> AttributeRemover_10
AttributeRemover_10
    REMOVE_ATTRS = OrganizationCollegeID,CollegeName
    -> DuplicateFilter_3
DuplicateFilter_3
    INPUT_ORDERED_CHOICE = Yes
    KEYATTR = OrganizationSubCollegeID
    UNIQUE -> DBO.OrganizationSubCollege (writer GEODATABASE_SDE_4)
    UNIQUE -> DBO.OrganizationSubCollege (writer GEODATABASE_SDE_6)
    UNIQUE -> DBO.OrganizationSubCollege (writer GEODATABASE_SDE_5)
DBO.OrganizationSubCollege (writer GEODATABASE_SDE_4)
    attributes: OrganizationSubCollegeID char(5), OrganizationCollegeKey char(3), SubCollegeName char(50), OBJECTID integer
DBO.OrganizationSubCollege (writer GEODATABASE_SDE_5)
    attributes: OrganizationSubCollegeID char(5), OrganizationCollegeKey char(3), SubCollegeName char(50), OBJECTID integer
DBO.OrganizationSubCollege (writer GEODATABASE_SDE_6)
    attributes: OrganizationSubCollegeID char(5), OrganizationCollegeKey char(3), SubCollegeName char(50), OBJECTID integer
AttributeCreator_10
    ATTR_TABLE = SET_TO OrganizationSubCollegeKey = @Value(OrganizationSubCollegeID)
    -> AttributeRemover_9
AttributeRemover_9
    REMOVE_ATTRS = OrganizationCollegeID,CollegeName
    -> DuplicateFilter
DuplicateFilter
    INPUT_ORDERED_CHOICE = Yes
    KEYATTR = OrganizationDepartmentID
    UNIQUE -> DBO.OrganizationDepartment (writer GEODATABASE_SDE_4)
    UNIQUE -> DBO.OrganizationDepartment (writer GEODATABASE_SDE_5)
    UNIQUE -> DBO.OrganizationDepartment (writer GEODATABASE_SDE_6)
DBO.OrganizationDepartment (writer GEODATABASE_SDE_4)
    attributes: OrganizationDepartmentID char(7), DepartmentName char(50), OBJECTID integer, OrganizationSubCollegeKey char(5)
DBO.OrganizationDepartment (writer GEODATABASE_SDE_5)
    attributes: OrganizationDepartmentID char(7), DepartmentName char(50), OBJECTID integer, OrganizationSubCollegeKey char(5)
DBO.OrganizationDepartment (writer GEODATABASE_SDE_6)
    attributes: OrganizationDepartmentID char(7), DepartmentName char(50), OBJECTID integer, OrganizationSubCollegeKey char(5)
dbo.FINANCIALORGANIZATIONCURRENTBIENNIUM (reader GEODATABASE_SDE_3)
    attributes: BienniumYear char(4), OrgCode char(10), BienniumInd char(2), EffectiveDate char(8), EffectiveDate6 char(6), OrgName char(30), CampusMailbox integer, AAUnit char(4), BienniumEndPurgeInd char(1), PCAStatus char(1), AgencyInd char(4), LibraryCode smallint, DefaultTask char(3), DefaultOption char(3), DefaultOroject char(6), LaborExpTask char(3), LaborExpOption char(3), LaborExpProject char(6), RevenueTask char(3), RevenueOption char(3), RevenueProject char(6), BudgetTask char(3), BudgetOption char(3), BudgetProject char(6), OverheadAllocationInd char(1), LaborDistributionInd char(1), LastActDate integer, ODSLoadTimestamp date, Parameter char(50), Value char(50),
      ParameterDesc char(150), ODSUpdateTimestamp date, OrgDept char(7)
    -> AttributeRenamer_11
AttributeRenamer_11
    ATTR_TABLE:
      RENAME_SET_DEFAULT OrgCode > ORGANIZATIONID
      RENAME_SET_DEFAULT OrgName > ORGANIZATION
    -> AttributeCreator_9
AttributeCreator_9
    ATTR_TABLE = SET_TO OrganizationDepartmentKey = @Left(@Value(ORGANIZATIONID),7)
    -> DBO.Organization (writer GEODATABASE_SDE_6)
    -> DBO.Organization (writer GEODATABASE_SDE_5)
    -> DBO.Organization (writer GEODATABASE_SDE_4)
DBO.Organization (writer GEODATABASE_SDE_4)
    attributes: ORGANIZATIONID char(50), ORGANIZATION char(50), OBJECTID integer, OrganizationDepartmentKey char(7)
DBO.Organization (writer GEODATABASE_SDE_5)
    attributes: ORGANIZATIONID char(50), ORGANIZATION char(50), OBJECTID integer, OrganizationDepartmentKey char(7)
DBO.Organization (writer GEODATABASE_SDE_6)
    attributes: ORGANIZATIONID char(50), ORGANIZATION char(50), OBJECTID integer, OrganizationDepartmentKey char(7)
DBO.FloorplanLine (reader GEODATABASE_SDE_1)
    attributes: OBJECTID integer, SITEID char(60), BUILDINGID char(60), FLOORCODE char(20), FLOORID char(60), SOURCELAYER char(24), SOURCEID char(30), SOURCEDWG char(60), LASTUPDATE date, LASTEDITOR char(30), SHAPE.STLength() double
    -> AttributeRenamer_14
    -> HullAccumulator
AttributeRenamer_14
    ATTR_TABLE:
      RENAME_SET_DEFAULT BUILDINGID > BUILDINGKEY
      RENAME_SET_DEFAULT FLOORID > FLOORKEY
      RENAME_SET_DEFAULT SOURCELAYER > LINETYPE
      RENAME_SET_DEFAULT LASTEDITOR > last_edited_user
      RENAME_SET_DEFAULT LASTUPDATE > last_edited_date
    -> senstivity_filter_5
    -> DBO.FloorplanLine_ALL (writer GEODATABASE_SDE_4)
    -> DBO.FloorplanLine_ALL (writer GEODATABASE_SDE_5)
    -> DBO.FloorplanLine_ALL (writer GEODATABASE_SDE_6)
senstivity_filter_5: Tester
    TEST_MODE = Automatic
    TEST_CLAUSE:
      TEST @Value(BUILDINGKEY) = 1212
      TEST @Value(BUILDINGKEY) = 1053
      TEST @Value(BUILDINGKEY) = 6327
      TEST @Value(BUILDINGKEY) = 6403
      TEST @Value(BUILDINGKEY) = 6563
    BOOL_OP = OR
    TEST_DESCRIPTION = ""
    FAILED -> DBO.FloorplanLine (writer GEODATABASE_SDE_4)
    FAILED -> DBO.FloorplanLine (writer GEODATABASE_SDE_5)
    FAILED -> DBO.FloorplanLine (writer GEODATABASE_SDE_6)
DBO.FloorplanLine (writer GEODATABASE_SDE_4)
    attributes: BUILDINGKEY char(50), FLOORKEY char(50), FLOORCODE char(5), LINETYPE char(50), created_user char(255), created_date date, last_edited_user char(255), last_edited_date date, SHAPE.STLength() double, OBJECTID integer
DBO.FloorplanLine (writer GEODATABASE_SDE_5)
    attributes: BUILDINGKEY char(50), FLOORKEY char(50), FLOORCODE char(5), LINETYPE char(50), created_user char(255), created_date date, last_edited_user char(255), last_edited_date date, SHAPE.STLength() double, OBJECTID integer
DBO.FloorplanLine (writer GEODATABASE_SDE_6)
    attributes: BUILDINGKEY char(50), FLOORKEY char(50), FLOORCODE char(5), LINETYPE char(50), created_user char(255), created_date date, last_edited_user char(255), last_edited_date date, SHAPE.STLength() double, OBJECTID integer
DBO.FloorplanLine_ALL (writer GEODATABASE_SDE_4)
    attributes: OBJECTID integer, BUILDINGKEY char(50), FLOORKEY char(50), FLOORCODE char(5), LINETYPE char(50), created_user char(255), created_date date, last_edited_user char(255), last_edited_date date, SHAPE.STLength() double
DBO.FloorplanLine_ALL (writer GEODATABASE_SDE_5)
    attributes: OBJECTID integer, BUILDINGKEY char(50), FLOORKEY char(50), FLOORCODE char(5), LINETYPE char(50), created_user char(255), created_date date, last_edited_user char(255), last_edited_date date, SHAPE.STLength() double
DBO.FloorplanLine_ALL (writer GEODATABASE_SDE_6)
    attributes: OBJECTID integer, BUILDINGKEY char(50), FLOORKEY char(50), FLOORCODE char(5), LINETYPE char(50), created_user char(255), created_date date, last_edited_user char(255), last_edited_date date, SHAPE.STLength() double
DBO.DrawingType_XP (reader GEODATABASE_SDE_1)
    attributes: OBJECTID integer, DRAWINGNAME char(100), BUILDINGID char(60), FLOORCODE char(20), FLOORID char(60), SITEID char(60), INTERIORSPACE char(3), FLOORPLANLINE char(3), FLOORAREA char(3), HASROUTE char(3)
    -> AttributeRenamer_12
AttributeRenamer_12
    ATTR_TABLE:
      RENAME_SET_DEFAULT BUILDINGID > BUILDINGKEY
      RENAME_SET_DEFAULT FLOORID > FLOORKEY
    -> DBO.DrawingType_XP (writer GEODATABASE_SDE_4)
    -> DBO.DrawingType_XP (writer GEODATABASE_SDE_5)
    -> DBO.DrawingType_XP (writer GEODATABASE_SDE_6)
DBO.DrawingType_XP (writer GEODATABASE_SDE_4)
    attributes: DRAWINGNAME char(100), BUILDINGKEY char(50), FLOORKEY char(50), FLOORCODE char(5), INTERIORSPACE char(3), FLOORPLANLINE char(3), FLOORAREA char(3), OBJECTID integer
DBO.DrawingType_XP (writer GEODATABASE_SDE_5)
    attributes: DRAWINGNAME char(100), BUILDINGKEY char(50), FLOORKEY char(50), FLOORCODE char(5), INTERIORSPACE char(3), FLOORPLANLINE char(3), FLOORAREA char(3), OBJECTID integer
DBO.DrawingType_XP (writer GEODATABASE_SDE_6)
    attributes: DRAWINGNAME char(100), BUILDINGKEY char(50), FLOORKEY char(50), FLOORCODE char(5), INTERIORSPACE char(3), FLOORPLANLINE char(3), FLOORAREA char(3), OBJECTID integer
DBO.DrawingType_RT (reader GEODATABASE_SDE_1)
    attributes: OBJECTID integer, DRAWINGNAME char(100), BUILDINGID char(60), FLOORCODE char(20), FLOORID char(60), SITEID char(60)
    -> AttributeRenamer_13
AttributeRenamer_13
    ATTR_TABLE:
      RENAME_SET_DEFAULT BUILDINGID > BUILDINGKEY
      RENAME_SET_DEFAULT FLOORID > FLOORKEY
    -> DBO.DrawingType_RT (writer GEODATABASE_SDE_4)
    -> DBO.DrawingType_RT (writer GEODATABASE_SDE_5)
    -> DBO.DrawingType_RT (writer GEODATABASE_SDE_6)
DBO.DrawingType_RT (writer GEODATABASE_SDE_4)
    attributes: DRAWINGNAME char(100), BUILDINGKEY char(50), FLOORKEY char(50), FLOORCODE char(5), OBJECTID integer
DBO.DrawingType_RT (writer GEODATABASE_SDE_5)
    attributes: DRAWINGNAME char(100), BUILDINGKEY char(50), FLOORKEY char(50), FLOORCODE char(5), OBJECTID integer
DBO.DrawingType_RT (writer GEODATABASE_SDE_6)
    attributes: DRAWINGNAME char(100), BUILDINGKEY char(50), FLOORKEY char(50), FLOORCODE char(5), OBJECTID integer
DBO.DrawingType_Outline (reader GEODATABASE_SDE_1)
    attributes: OBJECTID integer, DRAWINGNAME char(100), BUILDINGID char(60), SITEID char(60), FLOORPAGETEMPLATE char(3), ROOFOUTLINE char(3), BASEMAPOUTLINE char(3)
    -> AttributeRenamer_17
AttributeRenamer_17
    ATTR_TABLE = RENAME_SET_DEFAULT BUILDINGID > BUILDINGKEY
    -> DBO.DrawingType_Outline (writer GEODATABASE_SDE_4)
    -> DBO.DrawingType_Outline (writer GEODATABASE_SDE_5)
    -> DBO.DrawingType_Outline (writer GEODATABASE_SDE_6)
DBO.DrawingType_Outline (writer GEODATABASE_SDE_4)
    attributes: DRAWINGNAME char(100), BUILDINGKEY char(50), FLOORPAGETEMPLATE char(3), OBJECTID integer
DBO.DrawingType_Outline (writer GEODATABASE_SDE_5)
    attributes: DRAWINGNAME char(100), BUILDINGKEY char(50), FLOORPAGETEMPLATE char(3), OBJECTID integer
DBO.DrawingType_Outline (writer GEODATABASE_SDE_6)
    attributes: DRAWINGNAME char(100), BUILDINGKEY char(50), FLOORPAGETEMPLATE char(3), OBJECTID integer
dbo.PERSON (reader GEODATABASE_SDE_3)
    attributes: PersonKey integer, EmployeeID char(100), RegID char(100), PreferredName char(255), DisplayName char(255), LegalNamePrefix char(255), LegalFirstName char(255), LegalMiddleName char(255), LegalLastName char(255), LegalNameSuffix char(255), LegalFirstMiddleLastName char(255), LegalName char(255), PriorIdNbr char(100), UWNetID char(255), StudentID char(100), Birthdate date, CandidateID char(100), WorkdayPersonType char(255), USCitizenshipStatus char(100), RecordLoadDttm date
    -> AttributeRenamer_15
AttributeRenamer_15
    ATTR_TABLE:
      RENAME_SET_DEFAULT EmployeeID > EMPLOYEEID
      RENAME_SET_DEFAULT PreferredName > KNOWNAS
      RENAME_SET_DEFAULT DisplayName > LNAMEFNAME
      RENAME_SET_DEFAULT LegalFirstName > FIRSTNAME
      RENAME_SET_DEFAULT LegalLastName > LASTNAME
      RENAME_SET_DEFAULT UWNetID > EMAIL
    -> Tester_4
Tester_4
    TEST_MODE = Automatic
    TEST_CLAUSE = TEST KNOWNAS ATTRIBUTE_VALUE_NULL ""
    BOOL_OP = OR
    PASSED -> DBO.EmployeeInfo (writer GEODATABASE_SDE_4)
    PASSED -> DBO.EmployeeInfo (writer GEODATABASE_SDE_5)
    PASSED -> DBO.EmployeeInfo (writer GEODATABASE_SDE_6)
    FAILED -> AttributeCreator_14
AttributeCreator_14
    ATTR_TABLE = SET_TO KNOWNAS = @Value(LegalFirstMiddleLastName)
    -> DBO.EmployeeInfo (writer GEODATABASE_SDE_4)
    -> DBO.EmployeeInfo (writer GEODATABASE_SDE_5)
    -> DBO.EmployeeInfo (writer GEODATABASE_SDE_6)
DBO.EmployeeInfo (writer GEODATABASE_SDE_4)
    attributes: EMPLOYEEID char(50), ASSIGNMENTCOUNT integer, COSTCTR double, DEPARTMENT char(50), EMAIL char(255), FIRSTNAME char(255), KNOWNAS char(255), LASTNAME char(255), LNAMEFNAME char(140), PHOTOFILE char(100), SHIFT char(50), STATUS char(5), TELEPHONEEXT char(25), TITLE char(80), USERTYPE char(255), created_user char(255), created_date date, last_edited_user char(255), last_edited_date date, OBJECTID integer
DBO.EmployeeInfo (writer GEODATABASE_SDE_5)
    attributes: EMPLOYEEID char(50), ASSIGNMENTCOUNT integer, COSTCTR double, DEPARTMENT char(50), EMAIL char(255), FIRSTNAME char(255), KNOWNAS char(255), LASTNAME char(255), LNAMEFNAME char(140), PHOTOFILE char(100), SHIFT char(50), STATUS char(5), TELEPHONEEXT char(25), TITLE char(80), USERTYPE char(255), created_user char(255), created_date date, last_edited_user char(255), last_edited_date date, OBJECTID integer
DBO.EmployeeInfo (writer GEODATABASE_SDE_6)
    attributes: EMPLOYEEID char(50), ASSIGNMENTCOUNT integer, COSTCTR double, DEPARTMENT char(50), EMAIL char(255), FIRSTNAME char(255), KNOWNAS char(255), LASTNAME char(255), LNAMEFNAME char(140), PHOTOFILE char(100), SHIFT char(50), STATUS char(5), TELEPHONEEXT char(25), TITLE char(80), USERTYPE char(255), created_user char(255), created_date date, last_edited_user char(255), last_edited_date date, OBJECTID integer
dbo.FACILITY_CONDITION_DESCRIPTION (reader GEODATABASE_SDE_3)
    attributes: OFM_CONDITION char(1), Description char(50), Definition char(256)
    -> AttributeRenamer_26
AttributeRenamer_26
    ATTR_TABLE:
      RENAME_SET_DEFAULT OFM_CONDITION > BUILDINGCONDITIONID
      RENAME_SET_DEFAULT Description > BUILDINGCONDITION
      RENAME_SET_DEFAULT Definition > DEFINITION
    -> DBO.BuildingCondition (writer GEODATABASE_SDE_5)
    -> DBO.BuildingCondition (writer GEODATABASE_SDE_6)
    -> DBO.BuildingCondition (writer GEODATABASE_SDE_4)
DBO.BuildingCondition (writer GEODATABASE_SDE_4)
    attributes: BUILDINGCONDITIONID char(50), BUILDINGCONDITION char(50), DEFINITION char(256), OBJECTID integer
DBO.BuildingCondition (writer GEODATABASE_SDE_5)
    attributes: BUILDINGCONDITIONID char(50), BUILDINGCONDITION char(50), DEFINITION char(256), OBJECTID integer
DBO.BuildingCondition (writer GEODATABASE_SDE_6)
    attributes: BUILDINGCONDITIONID char(50), BUILDINGCONDITION char(50), DEFINITION char(256), OBJECTID integer
DBO.Building_Table (reader GEODATABASE_SDE_1)
    attributes: OBJECTID integer, SITEID char(60), FACILITYNO integer, BUILDINGID char(60), SENSITIVITY char(30), GROUNDELEV double, CALCROT double, LOCALROT double, MODPORTRAIT double, MODLANDSCAPE double
    -> AttributeRenamer_16
    -> FeatureMerger_15 [REQUESTOR]
AttributeRenamer_16
    ATTR_TABLE = RENAME_SET_DEFAULT BUILDINGID > BUILDINGKEY
    -> DBO.Building_Table (writer GEODATABASE_SDE_4)
    -> DBO.Building_Table (writer GEODATABASE_SDE_5)
    -> DBO.Building_Table (writer GEODATABASE_SDE_6)
DBO.Building_Table (writer GEODATABASE_SDE_4)
    attributes: FACILITYNO smallint, BUILDINGKEY char(50), SENSITIVITY char(30), GROUNDELEV double, CALCROT double, OBJECTID integer
DBO.Building_Table (writer GEODATABASE_SDE_5)
    attributes: FACILITYNO smallint, BUILDINGKEY char(50), SENSITIVITY char(30), GROUNDELEV double, CALCROT double, OBJECTID integer
DBO.Building_Table (writer GEODATABASE_SDE_6)
    attributes: FACILITYNO smallint, BUILDINGKEY char(50), SENSITIVITY char(30), GROUNDELEV double, CALCROT double, OBJECTID integer
dbo.FACILITY_TABLE (reader GEODATABASE_SDE_3)
    attributes: FACILITY_CODE char(4), FACILITY_TYPE char(4), STATUS char(3), NAME char(20), LONG_NAME char(100), SITE char(7), YEAR_CONSTRUCTED char(4), SECTOR char(3), REGISTERED_HISTORIC_SITE char(1), LAST_MAJOR_RENOVATION_DATE date, CONSTRUCTION_TYPE char(5), WEB_PLAN char(1), OFM_CITY_CODE char(4), OFM_COUNTY_CODE char(3), OFM_LEASE_START_DATE date, OFM_LEASE_END_DATE date, OFM_SITE_CODE char(3), OFM_LEGISLATIVE_DISTRICT char(2), OFM_CONDITION char(1), OFM_SITE_ADDRESS char(40), OFM_HSR char(3), BUILDING char(3), CENTER_FACILITY_LATITUDE double, CENTER_FACILITY_LONGITUDE double, MOD_USER char(30), MOD_DATE date, OS_USER char(30), CREATE_USER char(30), CREATE_DATE date, LEASED_OR_OWNED char(6),
      FACILITY_NUMBER smallint, GROSS_SQUARE_FEET integer, CONSTRUCTION_OR_PURCHASE_COST integer, LAST_MAJOR_RENOVATION_COST integer, AGGREGATE_FACILITY_NUMBER smallint, OFM_REPLACEMENT_COST_FACTOR integer
    -> DBO.Facility_Table (writer GEODATABASE_SDE_6)
    -> DBO.Facility_Table (writer GEODATABASE_SDE_5)
    -> DBO.Facility_Table (writer GEODATABASE_SDE_4)
    -> FeatureMerger_15 [SUPPLIER]
    -> dbo.FACILITY_TABLE (writer GEODATABASE_SDE_7)
FeatureMerger_15
    ATTR_ACCUM_MODE = Merge Supplier
    REJECT_NULL_MISSING_KEYS = No
    JOIN_KEYS = @Value(BUILDINGID) @Value(FACILITY_NUMBER) AUTO
    ATTR_CONFLICT_RES = Use Requestor
    IGNORE_NULLS = No
    PROCESS_DUPS = No
    SUPPLIERS_FIRST = No
    MERGE_TYPE = Attributes Only
    MERGED -> AttributeRenamer_27
    NOT_MERGED -> AttributeRenamer_27
AttributeRenamer_27
    ATTR_TABLE:
      RENAME_SET_DEFAULT NAME > SHORTNAME
      RENAME_SET_DEFAULT LONG_NAME > LONGNAME
    -> BuildingLookup (writer GEODATABASE_SDE_4)
    -> BuildingLookup (writer GEODATABASE_SDE_5)
    -> BuildingLookup (writer GEODATABASE_SDE_6)
dbo.FACILITY_TABLE (writer GEODATABASE_SDE_7)
    attributes: FACILITY_CODE char(4), FACILITY_TYPE char(4), STATUS char(3), NAME char(20), LONG_NAME char(100), SITE char(7), YEAR_CONSTRUCTED char(4), SECTOR char(3), REGISTERED_HISTORIC_SITE char(1), LAST_MAJOR_RENOVATION_DATE date, CONSTRUCTION_TYPE char(5), WEB_PLAN char(1), OFM_CITY_CODE char(4), OFM_COUNTY_CODE char(3), OFM_LEASE_START_DATE date, OFM_LEASE_END_DATE date, OFM_SITE_CODE char(3), OFM_LEGISLATIVE_DISTRICT char(2), OFM_CONDITION char(1), OFM_SITE_ADDRESS char(40), OFM_HSR char(3), BUILDING char(3), CENTER_FACILITY_LATITUDE double, CENTER_FACILITY_LONGITUDE double, MOD_USER char(30), MOD_DATE date, OS_USER char(30), CREATE_USER char(30), CREATE_DATE date, LEASED_OR_OWNED char(6),
      FACILITY_NUMBER smallint, GROSS_SQUARE_FEET integer, CONSTRUCTION_OR_PURCHASE_COST integer, LAST_MAJOR_RENOVATION_COST integer, AGGREGATE_FACILITY_NUMBER smallint, OFM_REPLACEMENT_COST_FACTOR integer
DBO.Facility_Table (writer GEODATABASE_SDE_4)
    attributes: FACILITY_CODE char(4), FACILITY_TYPE char(4), STATUS char(3), NAME char(20), LONG_NAME char(100), SITE char(7), YEAR_CONSTRUCTED char(4), SECTOR char(3), REGISTERED_HISTORIC_SITE char(1), LAST_MAJOR_RENOVATION_DATE date, CONSTRUCTION_TYPE char(5), WEB_PLAN char(1), OFM_CITY_CODE char(4), OFM_COUNTY_CODE char(3), OFM_LEASE_START_DATE date, OFM_LEASE_END_DATE date, OFM_SITE_CODE char(3), OFM_LEGISLATIVE_DISTRICT char(2), OFM_CONDITION char(1), OFM_SITE_ADDRESS char(40), OFM_HSR char(3), OFM_REPLACEMENT_COST_FACTOR integer, BUILDING char(3), CENTER_FACILITY_LATITUDE double, CENTER_FACILITY_LONGITUDE double, MOD_USER char(30), MOD_DATE date, OS_USER char(30), CREATE_USER char(30), CREATE_DATE date,
      LEASED_OR_OWNED char(6), FACILITY_NUMBER smallint, GROSS_SQUARE_FEET integer, CONSTRUCTION_OR_PURCHASE_COST integer, LAST_MAJOR_RENOVATION_COST integer, AGGREGATE_FACILITY_NUMBER smallint, OBJECTID integer
DBO.Facility_Table (writer GEODATABASE_SDE_5)
    attributes: FACILITY_CODE char(4), FACILITY_TYPE char(4), STATUS char(3), NAME char(20), LONG_NAME char(100), SITE char(7), YEAR_CONSTRUCTED char(4), SECTOR char(3), REGISTERED_HISTORIC_SITE char(1), LAST_MAJOR_RENOVATION_DATE date, CONSTRUCTION_TYPE char(5), WEB_PLAN char(1), OFM_CITY_CODE char(4), OFM_COUNTY_CODE char(3), OFM_LEASE_START_DATE date, OFM_LEASE_END_DATE date, OFM_SITE_CODE char(3), OFM_LEGISLATIVE_DISTRICT char(2), OFM_CONDITION char(1), OFM_SITE_ADDRESS char(40), OFM_HSR char(3), OFM_REPLACEMENT_COST_FACTOR integer, BUILDING char(3), CENTER_FACILITY_LATITUDE double, CENTER_FACILITY_LONGITUDE double, MOD_USER char(30), MOD_DATE date, OS_USER char(30), CREATE_USER char(30), CREATE_DATE date,
      LEASED_OR_OWNED char(6), FACILITY_NUMBER smallint, GROSS_SQUARE_FEET integer, CONSTRUCTION_OR_PURCHASE_COST integer, LAST_MAJOR_RENOVATION_COST integer, AGGREGATE_FACILITY_NUMBER smallint, OBJECTID integer
DBO.Facility_Table (writer GEODATABASE_SDE_6)
    attributes: FACILITY_CODE char(4), FACILITY_TYPE char(4), STATUS char(3), NAME char(20), LONG_NAME char(100), SITE char(7), YEAR_CONSTRUCTED char(4), SECTOR char(3), REGISTERED_HISTORIC_SITE char(1), LAST_MAJOR_RENOVATION_DATE date, CONSTRUCTION_TYPE char(5), WEB_PLAN char(1), OFM_CITY_CODE char(4), OFM_COUNTY_CODE char(3), OFM_LEASE_START_DATE date, OFM_LEASE_END_DATE date, OFM_SITE_CODE char(3), OFM_LEGISLATIVE_DISTRICT char(2), OFM_CONDITION char(1), OFM_SITE_ADDRESS char(40), OFM_HSR char(3), OFM_REPLACEMENT_COST_FACTOR integer, BUILDING char(3), CENTER_FACILITY_LATITUDE double, CENTER_FACILITY_LONGITUDE double, MOD_USER char(30), MOD_DATE date, OS_USER char(30), CREATE_USER char(30), CREATE_DATE date,
      LEASED_OR_OWNED char(6), FACILITY_NUMBER smallint, GROSS_SQUARE_FEET integer, CONSTRUCTION_OR_PURCHASE_COST integer, LAST_MAJOR_RENOVATION_COST integer, AGGREGATE_FACILITY_NUMBER smallint, OBJECTID integer

Bookmark: New Bookmark
HullAccumulator
    GROUP_BY = FLOORID
    HULLTYPE_PARAM = Convex ()
    3DMODE_PARAM = 2D
    HULL -> FeatureMerger_13 [REQUESTOR]
DBO.Floor_Table (reader GEODATABASE_SDE_1)
    attributes: OBJECTID integer, FLOORID char(60), BUILDINGID char(60), SITEID char(60), FLOORCODE char(20), SOURCEDWG char(100), SCHELEV integer, GROUNDOFFSET double, CALCROT double, LOCALROT double
    -> AttributeRemover_2
AttributeRemover_2
    REMOVE_ATTRS = SITEID,CALCROT,LOCALROT,OBJECTID
    -> AttributeRenamer_8
AttributeRenamer_8
    ATTR_TABLE = RENAME_SET_DEFAULT BUILDINGID > BUILDINGKEY
    -> DBO.Floor_Table (writer GEODATABASE_SDE_4)
    -> FeatureMerger_7 [REQUESTOR]
    -> DBO.Floor_Table (writer GEODATABASE_SDE_5)
    -> DBO.Floor_Table (writer GEODATABASE_SDE_6)
DBO.Floor_Table (writer GEODATABASE_SDE_4)
    attributes: BUILDINGKEY char(50), FLOORID char(50), FLOORCODE char(5), SOURCEDWG char(100), SCHELEV integer, GROUNDOFFSET double, OBJECTID integer
DBO.Floor_Table (writer GEODATABASE_SDE_5)
    attributes: BUILDINGKEY char(50), FLOORID char(50), FLOORCODE char(5), SOURCEDWG char(100), SCHELEV integer, GROUNDOFFSET double, OBJECTID integer
DBO.Floor_Table (writer GEODATABASE_SDE_6)
    attributes: BUILDINGKEY char(50), FLOORID char(50), FLOORCODE char(5), SOURCEDWG char(100), SCHELEV integer, GROUNDOFFSET double, OBJECTID integer
DBO.Floor_Level (reader GEODATABASE_SDE_1)
    attributes: OBJECTID integer, SITEID char(60), FLOORCODE char(20), FLOORLEVEL integer, NAMELONG char(100), NAMESHORT char(50)
    -> AttributeRemover_3
AttributeRemover_3
    REMOVE_ATTRS = SITEID,OBJECTID
    -> AttributeRenamer_10
AttributeRenamer_10
    ATTR_TABLE:
      RENAME_SET_DEFAULT NAMESHORT > FLOORSHORTNAME
      RENAME_SET_DEFAULT NAMELONG > FLOORLONGNAME
    -> DBO.Floor_Level (writer GEODATABASE_SDE_4)
    -> FeatureMerger_8 [SUPPLIER]
    -> DBO.Floor_Level (writer GEODATABASE_SDE_5)
    -> DBO.Floor_Level (writer GEODATABASE_SDE_6)
    -> FeatureMerger_4 [SUPPLIER]
DBO.FloorPageTemplate (reader GEODATABASE_SDE_1)
    attributes: OBJECTID integer, SITEID char(60), BUILDINGID char(60), CALCROT double, LOCALROT double, SOURCEID char(30), SOURCEDWG char(60), LASTUPDATE date, LASTEDITOR char(30), SHAPE.STArea() double, SHAPE.STLength() double
    -> AttributeRemover_4
AttributeRemover_4
    REMOVE_ATTRS = SHAPE.STLength(),SITEID,SHAPE.STArea(),LOCALROT,OBJECTID
    -> AttributeRenamer_22
AttributeRenamer_22
    ATTR_TABLE:
      RENAME_SET_DEFAULT BUILDINGID > BUILDINGKEY
      RENAME_SET_DEFAULT CALCROT > ROTATION
      RENAME_SET_DEFAULT LASTEDITOR > last_edited_user
      RENAME_SET_DEFAULT LASTUPDATE > last_edited_date
    -> FeatureMerger_7 [SUPPLIER]
    -> DBO.FloorPageTemplate (writer GEODATABASE_SDE_4)
    -> DBO.FloorPageTemplate (writer GEODATABASE_SDE_5)
    -> DBO.FloorPageTemplate (writer GEODATABASE_SDE_6)
FeatureMerger_7
    ATTR_ACCUM_MODE = Merge Supplier
    GEOM_TYPE = Build Polygons
    JOIN_KEYS = @Value(BUILDINGKEY) @Value(BUILDINGKEY) AUTO
    ATTR_CONFLICT_RES = Use Requestor
    IGNORE_NULLS = No
    CONNECT_Z_MODE = First Wins
    PROCESS_DUPS = Yes
    SUPPLIERS_FIRST = No
    MERGE_TYPE = Attributes and Geometry
    MERGED -> FeatureMerger_8 [REQUESTOR]
FeatureMerger_8
    ATTR_ACCUM_MODE = Merge Supplier
    JOIN_KEYS = @Value(FLOORCODE) @Value(FLOORCODE) AUTO
    ATTR_CONFLICT_RES = Use Requestor
    IGNORE_NULLS = No
    PROCESS_DUPS = No
    SUPPLIERS_FIRST = No
    MERGE_TYPE = Attributes Only
    MERGED -> FeatureMerger_9 [REQUESTOR]
DBO.FloorPageTemplate (writer GEODATABASE_SDE_4)
    attributes: BUILDINGKEY char(50), ROTATION double, SOURCEID char(30), SOURCEDWG char(60), last_edited_date date, last_edited_user char(255), OBJECTID integer, SHAPE.STArea() double, SHAPE.STLength() double
DBO.FloorPageTemplate (writer GEODATABASE_SDE_5)
    attributes: BUILDINGKEY char(50), ROTATION double, SOURCEID char(30), SOURCEDWG char(60), last_edited_date date, last_edited_user char(255), OBJECTID integer, SHAPE.STArea() double, SHAPE.STLength() double
DBO.FloorPageTemplate (writer GEODATABASE_SDE_6)
    attributes: BUILDINGKEY char(50), ROTATION double, SOURCEID char(30), SOURCEDWG char(60), last_edited_date date, last_edited_user char(255), OBJECTID integer, SHAPE.STArea() double, SHAPE.STLength() double
dbo.Floor (reader GEODATABASE_SDE_1)
    attributes: OBJECTID integer, FLOORID char(60), FLOORCODE char(20), NAMESHORT char(50), NAMELONG char(100), INTERIORSPACE char(3), FLOORPLANLINE char(3), FLOORAREA char(3), SCHELEV integer, GROUNDELEV double, FLOORLEVEL integer, STACKLEVEL double, SENSITIVITY char(30), DRAWINGNAME char(100), BUILDINGID char(60), BLDGNAME char(30), CALCROT double, LOCALROT double, DDPFLOORSORT char(71)
    -> AttributeRemover_5
    -> FeatureMerger_3 [SUPPLIER]
AttributeRemover_5
    REMOVE_ATTRS = FLOORPLANLINE,LOCALROT,NAMESHORT,INTERIORSPACE,DDPFLOORSORT,SENSITIVITY,OBJECTID,FLOORAREA,NAMELONG,DRAWINGNAME,FLOORLEVEL,GROUNDELEV,BLDGNAME
    -> BuildingPerFloor [REQUESTOR]
dbo.FACILITY_VIEW (reader GEODATABASE_SDE_3)
    attributes: SITE_DESCRIPTION char(36), FACILITY_NUMBER smallint, FACILITY_CODE char(4), NAME char(20), LONG_NAME char(100), FACILITY_TYPE_DESCRIPTION char(36), STATUS_DESCRIPTION char(30), LEASED_OR_OWNED char(6), GROSS_SQUARE_FEET integer, UsableSqft integer, AssignableSqft integer, FloorCount integer, RoomCount integer, Capacity integer, PrimaryRoomTypeGroup char(25), PrimaryRoomTypeGroupSqft integer, PrimaryUnit char(30), PrimaryUnitSqft double, PrimaryDept char(30), PrimaryDeptSqft double, YEAR_CONSTRUCTED char(4), SECTOR char(3), CONSTRUCTION_OR_PURCHASE_COST integer, LAST_MAJOR_RENOVATION_DATE date, LAST_MAJOR_RENOVATION_COST integer, REGISTERED_HISTORIC_SITE char(1), CONSTRUCTION_TYPE char(5), AGGREGATE_FACILITY_NUMBER smallint, OFM_CONDITION char(1), PrimaryStreetAddress char(104),
      CITY char(25), STATE char(20), POSTCODE char(10), COUNTY char(25), COUNTRY char(30), COUNTRY_CODE_2 char(3), CENTER_FACILITY_LATITUDE double, CENTER_FACILITY_LONGITUDE double, Depts char(2147483647)
    -> FeatureMerger_2 [SUPPLIER]
    -> FeatureMerger_9 [SUPPLIER]
FeatureMerger_9
    ATTR_ACCUM_MODE = Merge Supplier
    JOIN_KEYS = @Value(BUILDINGKEY) @Value(FACILITY_NUMBER) AUTO
    ATTR_CONFLICT_RES = Use Requestor
    IGNORE_NULLS = No
    PROCESS_DUPS = No
    SUPPLIERS_FIRST = No
    MERGE_TYPE = Attributes Only
    MERGED -> AttributeRenamer_21
AttributeRenamer_21
    ATTR_TABLE:
      RENAME_SET_DEFAULT BUILDINGID > BUILDINGKEY
      RENAME_SET_DEFAULT NAMESHORT > FLOORSHORTNAME
      RENAME_SET_DEFAULT NAMELONG > FLOORLONGNAME
      RENAME_SET_DEFAULT CALCROT > ROTATION
      RENAME_SET_DEFAULT LASTEDITOR > last_edited_user
      RENAME_SET_DEFAULT LASTUPDATE > last_edited_date
      RENAME_SET_DEFAULT NAME > BUILDINGNAME
    -> AttributeCreator_7
AttributeCreator_7
    ATTR_TABLE = SET_TO DDPFLOORSORT = @Value(BUILDINGKEY)_@Value(FLOORLEVEL)
    -> senstivity_filter_3
    -> DBO.FloorPage_ALL (writer GEODATABASE_SDE_4)
    -> DBO.FloorPage_ALL (writer GEODATABASE_SDE_5)
    -> DBO.FloorPage_ALL (writer GEODATABASE_SDE_6)
    -> FeatureMerger_13 [SUPPLIER]
FeatureMerger_13
    ATTR_ACCUM_MODE = Merge Supplier
    REJECT_NULL_MISSING_KEYS = No
    JOIN_KEYS = @Value(FLOORID) @Value(FLOORID) AUTO
    ATTR_CONFLICT_RES = Use Requestor
    IGNORE_NULLS = No
    PROCESS_DUPS = No
    SUPPLIERS_FIRST = No
    MERGE_TYPE = Attributes Only
    MERGED -> senstivity_filter_6
    MERGED -> DBO.FloorPage_Wrapper_ALL (writer GEODATABASE_SDE_4)
    MERGED -> DBO.FloorPage_Wrapper_ALL (writer GEODATABASE_SDE_5)
    MERGED -> DBO.FloorPage_Wrapper_ALL (writer GEODATABASE_SDE_6)
DBO.FloorPage_Wrapper_ALL (writer GEODATABASE_SDE_4)
    attributes: FLOORID char(50), FLOORCODE char(5), BUILDINGKEY char(50), FLOORSHORTNAME char(50), FLOORLONGNAME char(100), BUILDINGNAME char(50), ROTATION double, DDPFLOORSORT char(71), last_edited_date date, last_edited_user char(255)
DBO.FloorPage_Wrapper_ALL (writer GEODATABASE_SDE_5)
    attributes: FLOORID char(50), FLOORCODE char(5), BUILDINGKEY char(50), FLOORSHORTNAME char(50), FLOORLONGNAME char(100), BUILDINGNAME char(50), ROTATION double, DDPFLOORSORT char(71), last_edited_date date, last_edited_user char(255)
DBO.FloorPage_Wrapper_ALL (writer GEODATABASE_SDE_6)
    attributes: FLOORID char(50), FLOORCODE char(5), BUILDINGKEY char(50), FLOORSHORTNAME char(50), FLOORLONGNAME char(100), BUILDINGNAME char(50), ROTATION double, DDPFLOORSORT char(71), last_edited_date date, last_edited_user char(255)
senstivity_filter_6: Tester
    TEST_MODE = Automatic
    TEST_CLAUSE:
      TEST @Value(BUILDINGKEY) = 1212
      TEST @Value(BUILDINGKEY) = 1053
      TEST @Value(BUILDINGKEY) = 6327
      TEST @Value(BUILDINGKEY) = 6403
      TEST @Value(BUILDINGKEY) = 6563
    BOOL_OP = OR
    TEST_DESCRIPTION = ""
    PASSED -> DBO.FloorPage_Wrapper (writer GEODATABASE_SDE_4)
    PASSED -> DBO.FloorPage_Wrapper (writer GEODATABASE_SDE_5)
    PASSED -> DBO.FloorPage_Wrapper (writer GEODATABASE_SDE_6)
DBO.FloorPage_Wrapper (writer GEODATABASE_SDE_4)
    attributes: FLOORID char(50), FLOORCODE char(5), BUILDINGKEY char(50), FLOORSHORTNAME char(50), FLOORLONGNAME char(100), BUILDINGNAME char(50), ROTATION double, DDPFLOORSORT char(71), last_edited_date date, last_edited_user char(255)
DBO.FloorPage_Wrapper (writer GEODATABASE_SDE_5)
    attributes: FLOORID char(50), FLOORCODE char(5), BUILDINGKEY char(50), FLOORSHORTNAME char(50), FLOORLONGNAME char(100), BUILDINGNAME char(50), ROTATION double, DDPFLOORSORT char(71), last_edited_date date, last_edited_user char(255)
DBO.FloorPage_Wrapper (writer GEODATABASE_SDE_6)
    attributes: FLOORID char(50), FLOORCODE char(5), BUILDINGKEY char(50), FLOORSHORTNAME char(50), FLOORLONGNAME char(100), BUILDINGNAME char(50), ROTATION double, DDPFLOORSORT char(71), last_edited_date date, last_edited_user char(255)
DBO.FloorPage_ALL (writer GEODATABASE_SDE_4)
    attributes: OBJECTID integer, FLOORID char(50), FLOORCODE char(5), BUILDINGKEY char(50), FLOORSHORTNAME char(50), FLOORLONGNAME char(100), BUILDINGNAME char(50), ROTATION double, DDPFLOORSORT char(71), last_edited_date date, last_edited_user char(255), SHAPE.STArea() double, SHAPE.STLength() double
DBO.FloorPage_ALL (writer GEODATABASE_SDE_5)
    attributes: OBJECTID integer, FLOORID char(50), FLOORCODE char(5), BUILDINGKEY char(50), FLOORSHORTNAME char(50), FLOORLONGNAME char(100), BUILDINGNAME char(50), ROTATION double, DDPFLOORSORT char(71), last_edited_date date, last_edited_user char(255), SHAPE.STArea() double, SHAPE.STLength() double
DBO.FloorPage_ALL (writer GEODATABASE_SDE_6)
    attributes: OBJECTID integer, FLOORID char(50), FLOORCODE char(5), BUILDINGKEY char(50), FLOORSHORTNAME char(50), FLOORLONGNAME char(100), BUILDINGNAME char(50), ROTATION double, DDPFLOORSORT char(71), last_edited_date date, last_edited_user char(255), SHAPE.STArea() double, SHAPE.STLength() double
senstivity_filter_3: Tester
    TEST_MODE = Automatic
    TEST_CLAUSE:
      TEST @Value(BUILDINGKEY) = 1212
      TEST @Value(BUILDINGKEY) = 1053
      TEST @Value(BUILDINGKEY) = 6327
      TEST @Value(BUILDINGKEY) = 6403
      TEST @Value(BUILDINGKEY) = 6563
    BOOL_OP = OR
    TEST_DESCRIPTION = ""
    FAILED -> DBO.FloorPage (writer GEODATABASE_SDE_4)
    FAILED -> DBO.FloorPage (writer GEODATABASE_SDE_5)
    FAILED -> DBO.FloorPage (writer GEODATABASE_SDE_6)
DBO.FloorPage (writer GEODATABASE_SDE_4)
    attributes: FLOORID char(50), FLOORCODE char(5), BUILDINGKEY char(50), FLOORSHORTNAME char(50), FLOORLONGNAME char(100), BUILDINGNAME char(50), ROTATION double, DDPFLOORSORT char(71), last_edited_date date, last_edited_user char(255), OBJECTID integer, SHAPE.STArea() double, SHAPE.STLength() double
DBO.FloorPage (writer GEODATABASE_SDE_5)
    attributes: FLOORID char(50), FLOORCODE char(5), BUILDINGKEY char(50), FLOORSHORTNAME char(50), FLOORLONGNAME char(100), BUILDINGNAME char(50), ROTATION double, DDPFLOORSORT char(71), last_edited_date date, last_edited_user char(255), OBJECTID integer, SHAPE.STArea() double, SHAPE.STLength() double
DBO.FloorPage (writer GEODATABASE_SDE_6)
    attributes: FLOORID char(50), FLOORCODE char(5), BUILDINGKEY char(50), FLOORSHORTNAME char(50), FLOORLONGNAME char(100), BUILDINGNAME char(50), ROTATION double, DDPFLOORSORT char(71), last_edited_date date, last_edited_user char(255), OBJECTID integer, SHAPE.STArea() double, SHAPE.STLength() double
DBO.FloorArea (reader GEODATABASE_SDE_1)
    attributes: OBJECTID integer, SITEID char(60), BUILDINGID char(60), FLOORCODE char(20), FLOORID char(60), FLOORAREA double, SOURCEDWG char(60), LASTUPDATE date, LASTEDITOR char(30), SHAPE.STArea() double, SHAPE.STLength() double
    -> AttributeRenamer_7
    -> FeatureMerger_3 [REQUESTOR]
AttributeRenamer_7
    ATTR_TABLE = RENAME_SET_DEFAULT BUILDINGID > BUILDINGKEY
    -> senstivity_filter_4
    -> DBO.FloorArea_ALL (writer GEODATABASE_SDE_4)
    -> DBO.FloorArea_ALL (writer GEODATABASE_SDE_5)
    -> DBO.FloorArea_ALL (writer GEODATABASE_SDE_6)
DBO.FloorArea_ALL (writer GEODATABASE_SDE_4)
    attributes: OBJECTID integer, BUILDINGKEY char(50), FLOORID char(50), FLOORCODE char(5), FLOORAREA double, SOURCEDWG char(60), LASTUPDATE date, LASTEDITOR char(30), SHAPE.STArea() double, SHAPE.STLength() double
DBO.FloorArea_ALL (writer GEODATABASE_SDE_5)
    attributes: OBJECTID integer, BUILDINGKEY char(50), FLOORID char(50), FLOORCODE char(5), FLOORAREA double, SOURCEDWG char(60), LASTUPDATE date, LASTEDITOR char(30), SHAPE.STArea() double, SHAPE.STLength() double
DBO.FloorArea_ALL (writer GEODATABASE_SDE_6)
    attributes: OBJECTID integer, BUILDINGKEY char(50), FLOORID char(50), FLOORCODE char(5), FLOORAREA double, SOURCEDWG char(60), LASTUPDATE date, LASTEDITOR char(30), SHAPE.STArea() double, SHAPE.STLength() double
senstivity_filter_4: Tester
    TEST_MODE = Automatic
    TEST_CLAUSE:
      TEST @Value(BUILDINGKEY) = 1212
      TEST @Value(BUILDINGKEY) = 1053
      TEST @Value(BUILDINGKEY) = 6327
      TEST @Value(BUILDINGKEY) = 6403
      TEST @Value(BUILDINGKEY) = 6563
    BOOL_OP = OR
    TEST_DESCRIPTION = ""
    FAILED -> DBO.FloorArea (writer GEODATABASE_SDE_4)
    FAILED -> DBO.FloorArea (writer GEODATABASE_SDE_5)
    FAILED -> DBO.FloorArea (writer GEODATABASE_SDE_6)
DBO.FloorArea (writer GEODATABASE_SDE_4)
    attributes: BUILDINGKEY char(50), FLOORID char(50), FLOORCODE char(5), FLOORAREA double, SOURCEDWG char(60), LASTUPDATE date, LASTEDITOR char(30), SHAPE.STArea() double, SHAPE.STLength() double, OBJECTID integer
DBO.FloorArea (writer GEODATABASE_SDE_5)
    attributes: BUILDINGKEY char(50), FLOORID char(50), FLOORCODE char(5), FLOORAREA double, SOURCEDWG char(60), LASTUPDATE date, LASTEDITOR char(30), SHAPE.STArea() double, SHAPE.STLength() double, OBJECTID integer
DBO.FloorArea (writer GEODATABASE_SDE_6)
    attributes: BUILDINGKEY char(50), FLOORID char(50), FLOORCODE char(5), FLOORAREA double, SOURCEDWG char(60), LASTUPDATE date, LASTEDITOR char(30), SHAPE.STArea() double, SHAPE.STLength() double, OBJECTID integer
FeatureMerger_3 [off]
    ATTR_ACCUM_MODE = Merge Supplier
    REJECT_NULL_MISSING_KEYS = No
    JOIN_KEYS = @Value(FLOORID) @Value(FLOORID) AUTO
    ATTR_CONFLICT_RES = Use Requestor
    IGNORE_NULLS = No
    PROCESS_DUPS = No
    SUPPLIERS_FIRST = No
    MERGE_TYPE = Attributes Only
    MERGED -> 3DForcer
DBO.Building (reader GEODATABASE_SDE_2)
    attributes: OBJECTID integer, BUILDINGID char(50), FACILITY_CODE char(4), SHAPE.STArea() double, SHAPE.STLength() double, ADA char(15), ADDRESS char(120), ASSIGNMENTKEY char(50), BUILDINGTYPEKEY char(50), BUILDINGMANAGER char(50), CAPACITY smallint, CONDITIONKEY char(50), DESCRIPTION char(255), FACILITYKEY char(50), FACILITYNAME char(255), FLOORCOUNT integer, GROSSAREA double, LONGNAME char(100), MAINTBY char(50), NETAREA double, OCCUPANCY smallint, OPERHOURSKEY char(50), OWNEDBY char(50), REPLCOST double, SHORTNAME char(25), URL char(255), YEARBUILT smallint, USABLEAREA double, ASSIGNABLEAREA double, PERCENTUSABLE double,
      PERCENTASSIGNABLE double, OCCUPANCYRATE double, VACANCYRATE double, DENSITY double, created_date date, created_user char(255), last_edited_date date, last_edited_user char(255)
    -> FeatureMerger_2 [REQUESTOR]
FeatureMerger_2
    ATTR_ACCUM_MODE = Merge Supplier
    JOIN_KEYS = @Value(BUILDINGID) @Value(FACILITY_NUMBER) AUTO
    ATTR_CONFLICT_RES = Use Requestor
    IGNORE_NULLS = No
    PROCESS_DUPS = No
    SUPPLIERS_FIRST = No
    MERGE_TYPE = Attributes Only
    MERGED -> AttributeRenamer_2
AttributeRenamer_2
    ATTR_TABLE:
      RENAME_SET_DEFAULT LONG_NAME > LONGNAME
      RENAME_SET_DEFAULT NAME > SHORTNAME
      RENAME_SET_DEFAULT MOD_DATE > last_edited_date
      RENAME_SET_DEFAULT MOD_USER > last_edited_user
      RENAME_SET_DEFAULT CREATE_DATE > created_date
      RENAME_SET_DEFAULT CREATE_USER > created_user
      RENAME_SET_DEFAULT GROSS_SQUARE_FEET > GROSSAREA
      RENAME_SET_DEFAULT YEAR_CONSTRUCTED > YEARBUILT
      RENAME_SET_DEFAULT FloorCount > FLOORCOUNT
      RENAME_SET_DEFAULT OFM_CONDITION > CONDITIONKEY
      RENAME_SET_DEFAULT PrimaryStreetAddress > ADDRESS
      RENAME_SET_DEFAULT RoomCount > ROOMCOUNT
      RENAME_SET_DEFAULT Depts > DEPTS
      RENAME_SET_DEFAULT AssignableSqft > ASSIGNABLEAREA
      RENAME_SET_DEFAULT STATUS_DESCRIPTION > STATUS
      RENAME_SET_DEFAULT UsableSqft > USABLEAREA
    -> AttributeFilter
AttributeFilter
    ATTR_VALUES = <EMPTY>,<MISSING>,<NULL>,<UNFILTERED>,OWNED
    ATTR_NAME = LEASED_OR_OWNED
    <EMPTY> -> AttributeCreator_12
    <MISSING> -> AttributeCreator_12
    <NULL> -> AttributeCreator_12
    <UNFILTERED> -> AttributeCreator_12
    OWNED -> AttributeCreator_4
AttributeCreator_12
    ATTR_TABLE = SET_TO OWNEDBY = @Value(LEASED_OR_OWNED)UW
    -> DBO.Building
AttributeCreator_4
    ATTR_TABLE = SET_TO OWNEDBY = UW
    -> DBO.Building
Aggregator_2
    AGGREGATE_TYPE = Homogeneous Collection (If Possible)
    GROUP_BY = BUILDINGID
    SEP = ,
    ACCUM_ATTRS_NAME = Yes
    MODE = Geometry - Assemble One Level
    ORDERED = No
    AGGREGATE -> Dissolver_3
Dissolver_3
    CONNECT_Z_MODE = First Wins
    GROUP_BY = BUILDINGID
    NO_OVRLP = No
    ACCUM_INPUT_ATTRS = Get Attributes From One Representative Feature
    AREA -> Aggregator_4
Aggregator_4
    AGGREGATE_TYPE = Homogeneous Collection (If Possible)
    GROUP_BY = BUILDINGID
    SEP = ,
    ACCUM_ATTRS_NAME = Yes
    MODE = Geometry - Assemble One Level
    ORDERED = No
    AGGREGATE -> AttributeRenamer_4
AttributeRenamer_4
    ATTR_TABLE:
      RENAME_SET_DEFAULT BUILDINGID > B.BUILDINGID
      RENAME_SET_DEFAULT SHORTNAME > BUILDINGNAME
    -> AttributeRemover
AttributeRemover
    REMOVE_ATTRS = SHAPE.STLength(),OPERHOURSKEY,GROSSAREA,OWNEDBY,OCCUPANCYRATE,last_edited_date,ASSIGNMENTKEY,FACILITY_CODE,OBJECTID,OCCUPANCY,BUILDINGMANAGER,PERCENTASSIGNABLE,last_edited_user,ASSIGNABLEAREA,URL,BUILDINGTYPEKEY,FLOORCOUNT,DENSITY,NETAREA,YEARBUILT,CONDITIONKEY,MAINTBY,SHAPE.STArea(),USABLEAREA,created_date,ADDRESS,PERCENTUSABLE,created_user,CAPACITY,DESCRIPTION,LONGNAME,FACILITYNAME,VACANCYRATE
    -> BuildingPerFloor [SUPPLIER]
BuildingPerFloor: FeatureMerger [off]
    ATTR_ACCUM_MODE = Merge Supplier
    JOIN_KEYS = @Value(BUILDINGID) @Value(B.BUILDINGID) AUTO
    ATTR_CONFLICT_RES = Use Supplier
    IGNORE_NULLS = No
    PROCESS_DUPS = No
    SUPPLIERS_FIRST = No
    MERGE_TYPE = Attributes and Geometry
    MERGED -> AttributeRenamer_18
    NOT_MERGED -> AttributeRenamer_18
AttributeRenamer_18
    ATTR_TABLE = RENAME_SET_DEFAULT FT.FLOORID > B.FLOORID
    -> AttributeRenamer_19
AttributeRenamer_19
    ATTR_TABLE:
      RENAME_SET_DEFAULT B.FLOORID > FLOORID
      RENAME_SET_DEFAULT B.BUILDINGID > BUILDINGID
    -> 3DForcer
3DForcer
    KEEPZVAL = No
    ZVALATTR = @Value(SCHELEV) * 0.3048
    -> Aggregator_5
Aggregator_5
    AGGREGATE_TYPE = Homogeneous Collection (If Possible)
    GROUP_BY = FLOORID
    SEP = ,
    ACCUM_ATTRS_NAME = Yes
    MODE = Geometry - Assemble One Level
    ORDERED = No
    AGGREGATE -> AttributeRenamer_5
AttributeRenamer_5
    ATTR_TABLE:
      RENAME_SET_DEFAULT BUILDINGID > BUILDINGKEY
      RENAME_SET_DEFAULT FLOORAREA > GROSSAREA
      RENAME_SET_DEFAULT STACKLEVEL > VERTORDER
      RENAME_SET_DEFAULT CALCROT > ROTATION
    -> Dissolver
Dissolver
    CONNECT_Z_MODE = Extend
    GROUP_BY = FLOORID
    NO_OVRLP = No
    DIS_ATTR = .5
    ACCUM_INPUT_ATTRS = Yes
    AREA -> Aggregator
Aggregator
    AGGREGATE_TYPE = Homogeneous Collection (If Possible)
    GROUP_BY = FLOORID
    SEP = ,
    ACCUM_ATTRS_NAME = Yes
    MODE = Geometry - Assemble One Level
    ORDERED = No
    AGGREGATE -> FeatureMerger_4 [REQUESTOR]
    AGGREGATE -> DBO.Floor (writer GEODATABASE_SDE_5)
FeatureMerger_4
    ATTR_ACCUM_MODE = Merge Supplier
    REJECT_NULL_MISSING_KEYS = No
    JOIN_KEYS = @Value(FLOORCODE) @Value(FLOORCODE) AUTO
    ATTR_CONFLICT_RES = Use Requestor
    IGNORE_NULLS = No
    PROCESS_DUPS = No
    SUPPLIERS_FIRST = No
    MERGE_TYPE = Attributes Only
    MERGED -> GeometryValidator
GeometryValidator
    CONNECT_Z_MODE_TR = First Wins
    NULL_REMOVAL = NULL_REMOVAL
    REPAIR = Yes
    ISSUE_ATTR_NAME = _issues
    ARC_ENDPOINT_TOLERANCE_MODE = Auto
    SUMMARY = Detailed
    PRESETS = Custom
    TYPE_REPAIR = TYPE_REPAIR
    CONSECUTIVE_IDENTICAL_VERTICES_2D = CONSECUTIVE_IDENTICAL_VERTICES_2D
    DUP_COORDS_CHECK_Z = Yes
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    CHECK_HOLE_TOUCHING_POLYGON = No
    CONNECT_Z_MODE_SI = First Wins
    SELF_INTERSECTING = SELF_INTERSECTING
    PASSED -> AttributeCreator_6
    REPAIRED -> AttributeCreator_6
AttributeCreator_6
    ATTR_TABLE = SET_TO DDPFLOORSORT = @Value(BUILDINGKEY)_@Value(FLOORLEVEL)
    -> GeometryValidator_PASSED
GeometryValidator_PASSED: Junction
    -> FloorLookup (writer GEODATABASE_SDE_6)
    -> DBO.Floor (writer GEODATABASE_SDE_6)
    -> FloorLookup (writer GEODATABASE_SDE_4)
    -> DBO.Floor (writer GEODATABASE_SDE_5)
    -> DBO.Floor (writer GEODATABASE_SDE_4)
    -> FloorLookup (writer GEODATABASE_SDE_5)
DBO.Floor (writer GEODATABASE_SDE_4) [off]
    attributes: FLOORID char(50), BUILDINGKEY char(50), BUILDINGNAME char(50), FLOORSHORTNAME char(50), FLOORLONGNAME char(100), FLOORCODE char(5), GROSSAREA double, NETAREA double, ROTATION double, VERTORDER smallint, DDPFLOORSORT char(71), USABLEAREA double, ASSIGNABLEAREA double, PERCENTUSABLE double, PERCENTASSIGNABLE double, ROOF char(10), created_date date, created_user char(255), last_edited_date date, last_edited_user char(255), SHAPE.STArea() double, SHAPE.STLength() double, OBJECTID integer
DBO.Floor (writer GEODATABASE_SDE_5)
    attributes: FLOORID char(50), BUILDINGKEY char(50), BUILDINGNAME char(50), FLOORSHORTNAME char(50), FLOORLONGNAME char(100), FLOORCODE char(5), GROSSAREA double, NETAREA double, ROTATION double, VERTORDER smallint, DDPFLOORSORT char(71), USABLEAREA double, ASSIGNABLEAREA double, PERCENTUSABLE double, PERCENTASSIGNABLE double, ROOF char(10), created_date date, created_user char(255), last_edited_date date, last_edited_user char(255)
DBO.Floor (writer GEODATABASE_SDE_6)
    attributes: FLOORID char(50), BUILDINGKEY char(50), BUILDINGNAME char(50), FLOORSHORTNAME char(50), FLOORLONGNAME char(100), FLOORCODE char(5), GROSSAREA double, NETAREA double, ROTATION double, VERTORDER smallint, DDPFLOORSORT char(71), USABLEAREA double, ASSIGNABLEAREA double, PERCENTUSABLE double, PERCENTASSIGNABLE double, ROOF char(10), created_date date, created_user char(255), last_edited_date date, last_edited_user char(255), SHAPE.STArea() double, SHAPE.STLength() double, OBJECTID integer

Bookmark: new Building Lookup
BuildingLookup (writer GEODATABASE_SDE_4)
    attributes: BUILDINGID char(50), SHORTNAME char(50), LONGNAME char(100), SENSITIVITY char(30)
BuildingLookup (writer GEODATABASE_SDE_5)
    attributes: BUILDINGID char(50), SHORTNAME char(50), LONGNAME char(100), SENSITIVITY char(30)
BuildingLookup (writer GEODATABASE_SDE_6)
    attributes: BUILDINGID char(50), SHORTNAME char(50), LONGNAME char(100), SENSITIVITY char(30)

Bookmark: New Bookmark
DBO.InteriorSpace (reader GEODATABASE_SDE_1)
    attributes: OBJECTID integer, SITEID char(60), BUILDINGID char(60), FLOORCODE char(20), FLOORID char(60), ROOMNUMBER char(30), SPACEID char(60), SPACECLASS char(60), SPACEAREA double, SOURCEID char(30), SOURCEDWG char(60), LASTUPDATE date, LASTEDITOR char(30), SHAPE.STArea() double, SHAPE.STLength() double
    -> FeatureMerger [REQUESTOR]
dbo.ROOM (reader GEODATABASE_SDE_3)
    attributes: FACILITY_NUMBER smallint, FACILITY_CODE char(4), FLOOR_CODE char(4), ROOM_NUMBER char(20), SQUARE_FEET integer, ROOM_TYPE char(3), ORGANIZATION char(10), DESCRIPTION char(50), CAPACITY smallint, SURGE_SPACE char(1), LEASED_TO_EXTERNAL char(1), NEEDS_REASSIGNMENT char(1), EXTERIOR_WINDOW char(1), ASSIGNOR char(4), UNDERGRADS char(2), GRADS char(2), VISITING_PROFS char(2), SHARED char(1), ROOM_ASSIGN_COUNT smallint, NOTES char(256), FACROOM char(30), FLOOR_PLAN char(1), CONFIRM_USER char(30), CONFIRM_DATE date, CREATE_USER char(30), CREATE_DATE date, MOD_USER char(30), MOD_DATE date, OS_USER char(30), MOD_NETID char(30),
      MOD_NETID_DATE date
    -> AttributeCreator_3
AttributeCreator_3
    ATTR_TABLE = SET_TO SPACEID = @Value(FACILITY_NUMBER)_@Value(FLOOR_CODE)_@Value(ROOM_NUMBER)
    -> FeatureMerger [SUPPLIER]
FeatureMerger
    ATTR_ACCUM_MODE = Merge Supplier
    JOIN_KEYS = @Value(SPACEID) @Value(SPACEID) AUTO
    ATTR_CONFLICT_RES = Use Requestor
    IGNORE_NULLS = No
    PROCESS_DUPS = No
    SUPPLIERS_FIRST = No
    MERGE_TYPE = Attributes Only
    MERGED -> AttributeRenamer
    NOT_MERGED -> AttributeRenamer
AttributeRenamer
    ATTR_TABLE:
      RENAME_SET_DEFAULT SPACEAREA > NETAREA
      RENAME_SET_DEFAULT FLOORID > FLOORKEY
      RENAME_SET_DEFAULT BUILDINGID > BUILDINGKEY
      RENAME_SET_DEFAULT MOD_NETID > last_edited_user
      RENAME_SET_DEFAULT MOD_NETID_DATE > last_edited_date
      RENAME_SET_DEFAULT ORGANIZATION > ASSIGNMENTKEY
      RENAME_SET_DEFAULT CREATE_DATE > created_date
      RENAME_SET_DEFAULT CREATE_USER > created_user
      RENAME_SET_DEFAULT ORGANIZATION > ASSIGNMENTKEY
      RENAME_SET_DEFAULT ROOM_TYPE > SPACETYPECAT2KEY
    -> AttributeCreator_8
AttributeCreator_8
    ATTR_TABLE:
      SET_TO ASSIGNMENTCOLLEGEKEY = @Left(@Value(ASSIGNMENTKEY),3)
      SET_TO ASSIGNMENTDEPARTMENTKEY = @Left(@Value(ASSIGNMENTKEY),7)
      SET_TO ASSIGNMENTSUBCOLLEGEKEY = @Left(@Value(ASSIGNMENTKEY),5)
    -> TestFilter
TestFilter
    TEST_LIST = BOOL_OP,OR,COMPOSITE_TEST,<Unused>,TEST_CLAUSE,"TEST @Value(SPACETYPECAT2KEY) <= 099",space type <= 099
    DEFAULT_VALUE = <UNFILTERED>
    space type <= 099 -> AttributeCreator
    <UNFILTERED> -> AttributeCreator_2
AttributeCreator
    ATTR_TABLE:
      SET_TO ASSIGNABLE = No
      SET_TO ORGASSIGNABLE = No
    -> FeatureMerger_12 [REQUESTOR]
AttributeCreator_2
    ATTR_TABLE:
      SET_TO ASSIGNABLE = Yes
      SET_TO ORGASSIGNABLE = Yes
    -> FeatureMerger_12 [REQUESTOR]
dbo.ROOM_TYPE (reader GEODATABASE_SDE_3)
    attributes: ROOM_TYPE char(3), ROOM_TYPE_GROUP char(1), PRIMARY_USE char(20), SPACE_CATEGORY char(20), SCHOOL_OF_MEDICINE char(1), GENERAL char(1), HMC char(1), SECURITY_LEVEL char(1), REPLACEMENT_CODE char(3)
    -> AttributeRemover_8
AttributeRemover_8
    REMOVE_ATTRS = HMC,REPLACEMENT_CODE,SCHOOL_OF_MEDICINE,GENERAL,ROOM_TYPE_GROUP,SPACE_CATEGORY,SECURITY_LEVEL
    -> AttributeRenamer_3
AttributeRenamer_3
    ATTR_TABLE:
      RENAME_SET_DEFAULT ROOM_TYPE > SPACECAT2ID
      RENAME_SET_DEFAULT PRIMARY_USE > DESCRIPTION
    -> AttributeCreator_5
AttributeCreator_5
    ATTR_TABLE = SET_TO SPACECAT1KEY = @Left(@Value(SPACECAT2ID),1)00
    -> AttributeRemover_6
    -> Tester_3
AttributeRemover_6
    REMOVE_ATTRS = DESCRIPTION
    -> AttributeRenamer_23
AttributeRenamer_23
    ATTR_TABLE = RENAME_SET_DEFAULT SPACECAT1KEY > SPACECAT1ID
    -> Tester
Tester
    TEST_MODE = Automatic
    TEST_CLAUSE = TEST @Left(@Value(SPACECAT2ID),1) = 0
    BOOL_OP = OR
    TEST_DESCRIPTION = ""
    PASSED -> group_2
    FAILED -> group
group_2: AttributeCreator
    ATTR_TABLE = SET_TO spacecatgroup = @Left(@Value(SPACECAT2ID),2)
    -> AttributeFilter_2
AttributeFilter_2
    ATTR_VALUES = <EMPTY>,<MISSING>,<NULL>,<UNFILTERED>,01,02,03,04,05,06,07,09
    ATTR_NAME = spacecatgroup
    01 -> Building_Service
    02 -> Circulation
    03 -> Mechanical
    04 -> Mechanical
    05 -> Unclassified
    06 -> Unclassified
    07 -> Unclassified
    09 -> Building_Service
Building_Service: AttributeCreator
    ATTR_TABLE:
      SET_TO DESCRIPTION = Building Service
      SET_TO SPACECAT1ID = 010
    -> Non_Assignable
Circulation: AttributeCreator
    ATTR_TABLE:
      SET_TO DESCRIPTION = Circulation
      SET_TO SPACECAT1ID = 020
    -> Non_Assignable
Mechanical: AttributeCreator
    ATTR_TABLE:
      SET_TO DESCRIPTION = Mechanical
      SET_TO SPACECAT1ID = 030
    -> Non_Assignable
Non_Assignable: AttributeCreator
    ATTR_TABLE = SET_TO ORGASSIGNABLE = No
    -> Non_Assignable_OUTPUT
    -> DuplicateFilter_4
Unclassified: AttributeCreator
    ATTR_TABLE:
      SET_TO DESCRIPTION = Building Service
      SET_TO SPACECAT1ID = 000
    -> Assignable
group: AttributeCreator
    ATTR_TABLE = SET_TO spacecatgroup = @Left(@Value(SPACECAT2ID),1)
    -> AttributeFilter_3
AttributeFilter_3
    ATTR_VALUES = <EMPTY>,<MISSING>,<NULL>,<UNFILTERED>,1,2,3,4,5,6,7,8,9
    ATTR_NAME = spacecatgroup
    1 -> Classroom
    2 -> Labs
    3 -> Office
    4 -> Study
    5 -> Special
    6 -> General
    7 -> Support
    8 -> Health_Care
    9 -> Residential
Classroom: AttributeCreator
    ATTR_TABLE = SET_TO DESCRIPTION = Classrooms
    -> Assignable
Labs: AttributeCreator
    ATTR_TABLE = SET_TO DESCRIPTION = Laboratory Facilities
    -> Assignable
Office: AttributeCreator
    ATTR_TABLE = SET_TO DESCRIPTION = Office Facilities
    -> Assignable
Study: AttributeCreator
    ATTR_TABLE = SET_TO DESCRIPTION = Study Facilities
    -> Assignable
Special: AttributeCreator
    ATTR_TABLE = SET_TO DESCRIPTION = Special Use Facilities
    -> Assignable
General: AttributeCreator
    ATTR_TABLE = SET_TO DESCRIPTION = General Use Faclities
    -> Assignable
Support: AttributeCreator
    ATTR_TABLE = SET_TO DESCRIPTION = Support Facilities
    -> Assignable
Health_Care: AttributeCreator
    ATTR_TABLE = SET_TO DESCRIPTION = Health Care Facilities
    -> Assignable
Residential: AttributeCreator
    ATTR_TABLE = SET_TO DESCRIPTION = Residential Facilities
    -> Assignable
Assignable: AttributeCreator
    ATTR_TABLE = SET_TO ORGASSIGNABLE = Yes
    -> DuplicateFilter_4
    -> Non_Assignable_OUTPUT
Non_Assignable_OUTPUT: Junction
    -> AttributeRenamer_24
AttributeRenamer_24
    ATTR_TABLE = RENAME_SET_DEFAULT SPACECAT1ID > SPACETYPECAT1KEY
    -> FeatureMerger_12 [SUPPLIER]
FeatureMerger_12
    ATTR_ACCUM_MODE = Merge Supplier
    REJECT_NULL_MISSING_KEYS = No
    JOIN_KEYS = @Value(SPACETYPECAT2KEY) @Value(SPACECAT2ID) AUTO
    ATTR_CONFLICT_RES = Use Requestor
    IGNORE_NULLS = No
    PROCESS_DUPS = No
    SUPPLIERS_FIRST = No
    MERGE_TYPE = Attributes Only
    MERGED -> SpaceCat1isNotNull
    NOT_MERGED -> SpaceCat1isNotNull
SpaceCat1isNotNull: Tester
    TEST_MODE = Automatic
    TEST_CLAUSE = TEST @Value(SPACETYPECAT1KEY) ATTRIBUTE_HAS_VALUE ""
    BOOL_OP = OR
    TEST_DESCRIPTION = ""
    PASSED -> OrgIsAssigned
    FAILED -> Space_Cat_to_590
Space_Cat_to_590: AttributeCreator
    ATTR_TABLE:
      SET_TO SPACETYPECAT2KEY = 590
      SET_TO SPACETYPECAT1KEY = 500
    -> OrgIsAssigned
OrgIsAssigned: Tester
    TEST_MODE = Automatic
    TEST_CLAUSE = TEST @Value(ASSIGNMENTKEY) ATTRIBUTE_HAS_VALUE ""
    BOOL_OP = OR
    TEST_DESCRIPTION = ""
    PASSED -> AttributeCreator_13_OUTPUT
    FAILED -> AttributeCreator_13
AttributeCreator_13
    ATTR_TABLE:
      SET_TO ASSIGNMENTKEY = UNKNOWN
      SET_TO ASSIGNMENTCOLLEGEKEY = UNK
      SET_TO ASSIGNMENTSUBCOLLEGEKEY = UNKNO
      SET_TO ASSIGNMENTDEPARTMENTKEY = UNKNOWN
    -> AttributeCreator_13_OUTPUT
AttributeCreator_13_OUTPUT: Junction
    -> CenterPointReplacer
    -> DBO.InteriorSpace_ALL (writer GEODATABASE_SDE_5)
    -> DBO.InteriorSpace_ALL (writer GEODATABASE_SDE_4)
    -> DBO.InteriorSpace_ALL (writer GEODATABASE_SDE_6)
    -> senstivity_filter
    -> InteriorSpaceLookup (writer GEODATABASE_SDE_4)
    -> InteriorSpaceLookup (writer GEODATABASE_SDE_5)
    -> InteriorSpaceLookup (writer GEODATABASE_SDE_6)
senstivity_filter: Tester
    TEST_MODE = Automatic
    TEST_CLAUSE:
      TEST @Value(BUILDINGKEY) = 1212
      TEST @Value(BUILDINGKEY) = 1053
      TEST @Value(BUILDINGKEY) = 6327
      TEST @Value(BUILDINGKEY) = 6403
      TEST @Value(BUILDINGKEY) = 6563
    BOOL_OP = OR
    TEST_DESCRIPTION = ""
    FAILED -> DBO.InteriorSpace (writer GEODATABASE_SDE_5)
    FAILED -> DBO.InteriorSpace (writer GEODATABASE_SDE_4)
    FAILED -> DBO.InteriorSpace (writer GEODATABASE_SDE_6)
DBO.InteriorSpace (writer GEODATABASE_SDE_4)
    attributes: SPACEID char(50), ASSIGNMENTKEY char(50), CAPACITY integer, PHYSICALCAPACITY integer, DESCRIPTION char(255), FLOORKEY char(50), FLOORCODE char(5), GROSSAREA double, LONGNAME char(100), NETAREA double, SHORTNAME char(25), SPACETYPECAT1KEY char(5), SPACETYPECAT2KEY char(5), SPACEUSECAT1KEY char(5), SPACEUSECAT2KEY char(5), USABLE char(10), ASSIGNABLE char(10), ORGASSIGNABLE char(10), created_date date, created_user char(255), last_edited_date date, last_edited_user char(255), SHAPE.STArea() double, SHAPE.STLength() double, OBJECTID integer, ACCESSTYPEKEY char(50), ADA char(15), ALLOCATIONPCT double, CEILINGHEIGHT double, OCCUPANCY smallint,
      SECTIONKEY char(50), SPACESTANDARDKEY char(50), AVAILABILITY char(50), VACANCY smallint, ROOMNUMBER char(25), BUILDINGKEY char(50), ASSIGNMENTCOLLEGEKEY char(3), ASSIGNMENTDEPARTMENTKEY char(7), ASSIGNMENTSUBCOLLEGEKEY char(5)
DBO.InteriorSpace (writer GEODATABASE_SDE_5)
    attributes: SPACEID char(50), ACCESSTYPEKEY char(50), ADA char(15), ALLOCATIONPCT double, ASSIGNMENTKEY char(50), CAPACITY integer, PHYSICALCAPACITY integer, CEILINGHEIGHT double, DESCRIPTION char(255), FLOORKEY char(50), FLOORCODE char(5), GROSSAREA double, LONGNAME char(100), NETAREA double, OCCUPANCY smallint, SECTIONKEY char(50), SHORTNAME char(25), SPACESTANDARDKEY char(50), SPACETYPECAT1KEY char(5), SPACETYPECAT2KEY char(5), SPACEUSECAT1KEY char(5), SPACEUSECAT2KEY char(5), AVAILABILITY char(50), USABLE char(10), ASSIGNABLE char(10), ORGASSIGNABLE char(10), VACANCY smallint, created_date date, created_user char(255), last_edited_date date,
      last_edited_user char(255), SHAPE.STArea() double, SHAPE.STLength() double, OBJECTID integer, ROOMNUMBER char(25), BUILDINGKEY char(50), ASSIGNMENTCOLLEGEKEY char(3), ASSIGNMENTDEPARTMENTKEY char(7), ASSIGNMENTSUBCOLLEGEKEY char(5)
DBO.InteriorSpace (writer GEODATABASE_SDE_6)
    attributes: SPACEID char(50), ACCESSTYPEKEY char(50), ADA char(15), ALLOCATIONPCT double, ASSIGNMENTKEY char(50), CAPACITY integer, PHYSICALCAPACITY integer, CEILINGHEIGHT double, DESCRIPTION char(255), FLOORKEY char(50), FLOORCODE char(5), GROSSAREA double, LONGNAME char(100), NETAREA double, OCCUPANCY smallint, SECTIONKEY char(50), SHORTNAME char(25), SPACESTANDARDKEY char(50), SPACETYPECAT1KEY char(5), SPACETYPECAT2KEY char(5), SPACEUSECAT1KEY char(5), SPACEUSECAT2KEY char(5), AVAILABILITY char(50), USABLE char(10), ASSIGNABLE char(10), ORGASSIGNABLE char(10), VACANCY smallint, created_date date, created_user char(255), last_edited_date date,
      last_edited_user char(255), SHAPE.STArea() double, SHAPE.STLength() double, OBJECTID integer, ROOMNUMBER char(25), BUILDINGKEY char(50), ASSIGNMENTCOLLEGEKEY char(3), ASSIGNMENTDEPARTMENTKEY char(7), ASSIGNMENTSUBCOLLEGEKEY char(5)
DBO.InteriorSpace_ALL (writer GEODATABASE_SDE_4)
    attributes: OBJECTID integer, SPACEID char(50), ALLOCATIONPCT double, ASSIGNMENTKEY char(50), CAPACITY integer, PHYSICALCAPACITY integer, DESCRIPTION char(255), FLOORKEY char(50), FLOORCODE char(5), GROSSAREA double, LONGNAME char(100), SHORTNAME char(25), SPACETYPECAT1KEY char(5), SPACETYPECAT2KEY char(5), SPACEUSECAT1KEY char(5), SPACEUSECAT2KEY char(5), AVAILABILITY char(50), USABLE char(10), ASSIGNABLE char(10), ORGASSIGNABLE char(10), created_date date, created_user char(255), last_edited_date date, last_edited_user char(255), SHAPE.STArea() double, SHAPE.STLength() double, ROOMNUMBER char(25), ACCESSTYPEKEY char(50), ADA char(15), CEILINGHEIGHT double,
      NETAREA double, OCCUPANCY smallint, SECTIONKEY char(50), SPACESTANDARDKEY char(50), VACANCY smallint, BUILDINGKEY char(50), ASSIGNMENTCOLLEGEKEY char(3), ASSIGNMENTDEPARTMENTKEY char(7), ASSIGNMENTSUBCOLLEGEKEY char(5)
DBO.InteriorSpace_ALL (writer GEODATABASE_SDE_5)
    attributes: OBJECTID integer, SPACEID char(50), ALLOCATIONPCT double, ASSIGNMENTKEY char(50), CAPACITY integer, PHYSICALCAPACITY integer, DESCRIPTION char(255), FLOORKEY char(50), FLOORCODE char(5), GROSSAREA double, LONGNAME char(100), SHORTNAME char(25), SPACETYPECAT1KEY char(5), SPACETYPECAT2KEY char(5), SPACEUSECAT1KEY char(5), SPACEUSECAT2KEY char(5), AVAILABILITY char(50), USABLE char(10), ASSIGNABLE char(10), ORGASSIGNABLE char(10), created_date date, created_user char(255), last_edited_date date, last_edited_user char(255), SHAPE.STArea() double, SHAPE.STLength() double, ROOMNUMBER char(25), ACCESSTYPEKEY char(50), ADA char(15), CEILINGHEIGHT double,
      NETAREA double, OCCUPANCY smallint, SECTIONKEY char(50), SPACESTANDARDKEY char(50), VACANCY smallint, BUILDINGKEY char(50), ASSIGNMENTCOLLEGEKEY char(3), ASSIGNMENTDEPARTMENTKEY char(7), ASSIGNMENTSUBCOLLEGEKEY char(5)
DBO.InteriorSpace_ALL (writer GEODATABASE_SDE_6)
    attributes: OBJECTID integer, SPACEID char(50), ALLOCATIONPCT double, ASSIGNMENTKEY char(50), CAPACITY integer, PHYSICALCAPACITY integer, DESCRIPTION char(255), FLOORKEY char(50), FLOORCODE char(5), GROSSAREA double, LONGNAME char(100), SHORTNAME char(25), SPACETYPECAT1KEY char(5), SPACETYPECAT2KEY char(5), SPACEUSECAT1KEY char(5), SPACEUSECAT2KEY char(5), AVAILABILITY char(50), USABLE char(10), ASSIGNABLE char(10), ORGASSIGNABLE char(10), created_date date, created_user char(255), last_edited_date date, last_edited_user char(255), SHAPE.STArea() double, SHAPE.STLength() double, ROOMNUMBER char(25), ACCESSTYPEKEY char(50), ADA char(15), CEILINGHEIGHT double,
      NETAREA double, OCCUPANCY smallint, SECTIONKEY char(50), SPACESTANDARDKEY char(50), VACANCY smallint, BUILDINGKEY char(50), ASSIGNMENTCOLLEGEKEY char(3), ASSIGNMENTDEPARTMENTKEY char(7), ASSIGNMENTSUBCOLLEGEKEY char(5)
CenterPointReplacer
    MODE = Inside Point
    POINT -> DBO.InteriorSpace_Point_ALL (writer GEODATABASE_SDE_5)
    POINT -> senstivity_filter_2
    POINT -> DBO.InteriorSpace_Point_ALL (writer GEODATABASE_SDE_4)
    POINT -> DBO.InteriorSpace_Point_ALL (writer GEODATABASE_SDE_6)
DBO.InteriorSpace_Point_ALL (writer GEODATABASE_SDE_4)
    attributes: OBJECTID integer, SPACEID char(50), ALLOCATIONPCT double, ASSIGNMENTKEY char(50), CAPACITY integer, PHYSICALCAPACITY integer, DESCRIPTION char(255), FLOORKEY char(50), FLOORCODE char(5), GROSSAREA double, LONGNAME char(100), SHORTNAME char(25), SPACETYPECAT1KEY char(5), SPACETYPECAT2KEY char(5), SPACEUSECAT1KEY char(5), SPACEUSECAT2KEY char(5), AVAILABILITY char(50), USABLE char(10), ASSIGNABLE char(10), ORGASSIGNABLE char(10), created_date date, created_user char(255), last_edited_date date, last_edited_user char(255), ROOMNUMBER char(25), ACCESSTYPEKEY char(50), ADA char(15), CEILINGHEIGHT double, NETAREA double, OCCUPANCY smallint,
      SECTIONKEY char(50), SPACESTANDARDKEY char(50), VACANCY smallint, BUILDINGKEY char(50), ASSIGNMENTCOLLEGEKEY char(3), ASSIGNMENTDEPARTMENTKEY char(7), ASSIGNMENTSUBCOLLEGEKEY char(5)
DBO.InteriorSpace_Point_ALL (writer GEODATABASE_SDE_5)
    attributes: OBJECTID integer, SPACEID char(50), ALLOCATIONPCT double, ASSIGNMENTKEY char(50), CAPACITY integer, PHYSICALCAPACITY integer, DESCRIPTION char(255), FLOORKEY char(50), FLOORCODE char(5), GROSSAREA double, LONGNAME char(100), SHORTNAME char(25), SPACETYPECAT1KEY char(5), SPACETYPECAT2KEY char(5), SPACEUSECAT1KEY char(5), SPACEUSECAT2KEY char(5), AVAILABILITY char(50), USABLE char(10), ASSIGNABLE char(10), ORGASSIGNABLE char(10), created_date date, created_user char(255), last_edited_date date, last_edited_user char(255), ROOMNUMBER char(25), ACCESSTYPEKEY char(50), ADA char(15), CEILINGHEIGHT double, NETAREA double, OCCUPANCY smallint,
      SECTIONKEY char(50), SPACESTANDARDKEY char(50), VACANCY smallint, BUILDINGKEY char(50), ASSIGNMENTCOLLEGEKEY char(3), ASSIGNMENTDEPARTMENTKEY char(7), ASSIGNMENTSUBCOLLEGEKEY char(5)
DBO.InteriorSpace_Point_ALL (writer GEODATABASE_SDE_6)
    attributes: OBJECTID integer, SPACEID char(50), ALLOCATIONPCT double, ASSIGNMENTKEY char(50), CAPACITY integer, PHYSICALCAPACITY integer, DESCRIPTION char(255), FLOORKEY char(50), FLOORCODE char(5), GROSSAREA double, LONGNAME char(100), SHORTNAME char(25), SPACETYPECAT1KEY char(5), SPACETYPECAT2KEY char(5), SPACEUSECAT1KEY char(5), SPACEUSECAT2KEY char(5), AVAILABILITY char(50), USABLE char(10), ASSIGNABLE char(10), ORGASSIGNABLE char(10), created_date date, created_user char(255), last_edited_date date, last_edited_user char(255), ROOMNUMBER char(25), ACCESSTYPEKEY char(50), ADA char(15), CEILINGHEIGHT double, NETAREA double, OCCUPANCY smallint,
      SECTIONKEY char(50), SPACESTANDARDKEY char(50), VACANCY smallint, BUILDINGKEY char(50), ASSIGNMENTCOLLEGEKEY char(3), ASSIGNMENTDEPARTMENTKEY char(7), ASSIGNMENTSUBCOLLEGEKEY char(5)
senstivity_filter_2: Tester
    TEST_MODE = Automatic
    TEST_CLAUSE:
      TEST @Value(BUILDINGKEY) = 1212
      TEST @Value(BUILDINGKEY) = 1053
      TEST @Value(BUILDINGKEY) = 6327
      TEST @Value(BUILDINGKEY) = 6403
      TEST @Value(BUILDINGKEY) = 6563
    BOOL_OP = OR
    TEST_DESCRIPTION = ""
    FAILED -> DBO.InteriorSpace_Point (writer GEODATABASE_SDE_5)
    FAILED -> DBO.InteriorSpace_Point (writer GEODATABASE_SDE_4)
    FAILED -> DBO.InteriorSpace_Point (writer GEODATABASE_SDE_6)
DBO.InteriorSpace_Point (writer GEODATABASE_SDE_4)
    attributes: OBJECTID integer, SPACEID char(50), ALLOCATIONPCT double, ASSIGNMENTKEY char(50), CAPACITY integer, PHYSICALCAPACITY integer, DESCRIPTION char(255), FLOORKEY char(50), FLOORCODE char(5), GROSSAREA double, LONGNAME char(100), SHORTNAME char(25), SPACETYPECAT1KEY char(5), SPACETYPECAT2KEY char(5), SPACEUSECAT1KEY char(5), SPACEUSECAT2KEY char(5), AVAILABILITY char(50), USABLE char(10), ASSIGNABLE char(10), ORGASSIGNABLE char(10), created_date date, created_user char(255), last_edited_date date, last_edited_user char(255), ROOMNUMBER char(25), ACCESSTYPEKEY char(50), ADA char(15), CEILINGHEIGHT double, NETAREA double, OCCUPANCY smallint,
      SECTIONKEY char(50), SPACESTANDARDKEY char(50), VACANCY smallint, BUILDINGKEY char(50), ASSIGNMENTCOLLEGEKEY char(3), ASSIGNMENTDEPARTMENTKEY char(7), ASSIGNMENTSUBCOLLEGEKEY char(5)
DBO.InteriorSpace_Point (writer GEODATABASE_SDE_5)
    attributes: OBJECTID integer, SPACEID char(50), ALLOCATIONPCT double, ASSIGNMENTKEY char(50), CAPACITY integer, PHYSICALCAPACITY integer, DESCRIPTION char(255), FLOORKEY char(50), FLOORCODE char(5), GROSSAREA double, LONGNAME char(100), SHORTNAME char(25), SPACETYPECAT1KEY char(5), SPACETYPECAT2KEY char(5), SPACEUSECAT1KEY char(5), SPACEUSECAT2KEY char(5), AVAILABILITY char(50), USABLE char(10), ASSIGNABLE char(10), ORGASSIGNABLE char(10), created_date date, created_user char(255), last_edited_date date, last_edited_user char(255), ROOMNUMBER char(25), ACCESSTYPEKEY char(50), ADA char(15), CEILINGHEIGHT double, NETAREA double, OCCUPANCY smallint,
      SECTIONKEY char(50), SPACESTANDARDKEY char(50), VACANCY smallint, BUILDINGKEY char(50), ASSIGNMENTCOLLEGEKEY char(3), ASSIGNMENTDEPARTMENTKEY char(7), ASSIGNMENTSUBCOLLEGEKEY char(5)
DBO.InteriorSpace_Point (writer GEODATABASE_SDE_6)
    attributes: OBJECTID integer, SPACEID char(50), ALLOCATIONPCT double, ASSIGNMENTKEY char(50), CAPACITY integer, PHYSICALCAPACITY integer, DESCRIPTION char(255), FLOORKEY char(50), FLOORCODE char(5), GROSSAREA double, LONGNAME char(100), SHORTNAME char(25), SPACETYPECAT1KEY char(5), SPACETYPECAT2KEY char(5), SPACEUSECAT1KEY char(5), SPACEUSECAT2KEY char(5), AVAILABILITY char(50), USABLE char(10), ASSIGNABLE char(10), ORGASSIGNABLE char(10), created_date date, created_user char(255), last_edited_date date, last_edited_user char(255), ROOMNUMBER char(25), ACCESSTYPEKEY char(50), ADA char(15), CEILINGHEIGHT double, NETAREA double, OCCUPANCY smallint,
      SECTIONKEY char(50), SPACESTANDARDKEY char(50), VACANCY smallint, BUILDINGKEY char(50), ASSIGNMENTCOLLEGEKEY char(3), ASSIGNMENTDEPARTMENTKEY char(7), ASSIGNMENTSUBCOLLEGEKEY char(5)
DuplicateFilter_4
    INPUT_ORDERED_CHOICE = No
    KEYATTR = SPACECAT1ID
    UNIQUE -> DBO.SpaceClassificationLevel1 (writer GEODATABASE_SDE_6)
    UNIQUE -> DBO.SpaceClassificationLevel1 (writer GEODATABASE_SDE_4)
    UNIQUE -> DBO.SpaceClassificationLevel1 (writer GEODATABASE_SDE_5)
DBO.SpaceClassificationLevel1 (writer GEODATABASE_SDE_4)
    attributes: SPACECAT1ID char(5), DESCRIPTION char(50), ORGASSIGNABLE char(5), OBJECTID integer
DBO.SpaceClassificationLevel1 (writer GEODATABASE_SDE_5)
    attributes: SPACECAT1ID char(5), DESCRIPTION char(50), ORGASSIGNABLE char(5), OBJECTID integer
DBO.SpaceClassificationLevel1 (writer GEODATABASE_SDE_6)
    attributes: SPACECAT1ID char(5), DESCRIPTION char(50), ORGASSIGNABLE char(5), OBJECTID integer

Bookmark: doesn't change, don't update
Tester_3 [off]
    TEST_MODE = Automatic
    TEST_CLAUSE = TEST @Left(@Value(SPACECAT2ID),1) = 0
    BOOL_OP = OR
    TEST_DESCRIPTION = ""
    PASSED -> group_3 [off]
    FAILED -> DBO.SpaceClassificationLevel2 (writer GEODATABASE_SDE_6) [off]
    FAILED -> DBO.SpaceClassificationLevel2 (writer GEODATABASE_SDE_5) [off]
    FAILED -> DBO.SpaceClassificationLevel2 (writer GEODATABASE_SDE_4) [off]
group_3: AttributeCreator [off]
    ATTR_TABLE = SET_TO spacecatgroup = @Left(@Value(SPACECAT2ID),2)
    -> AttributeFilter_4 [off]
AttributeFilter_4 [off]
    ATTR_VALUES = <EMPTY>,<MISSING>,<NULL>,<UNFILTERED>,01,02,03,04,05,06,07,09
    ATTR_NAME = spacecatgroup
    01 -> Building_Service_2 [off]
    02 -> Circulation_2 [off]
    03 -> Mechanical_2 [off]
    04 -> Mechanical_2 [off]
    05 -> Unclassified_2 [off]
    06 -> Unclassified_2 [off]
    07 -> Unclassified_2 [off]
    09 -> Building_Service_2 [off]
Building_Service_2: AttributeCreator [off]
    ATTR_TABLE = SET_TO SPACECAT1KEY = 010
    -> Building_Service_2_OUTPUT [off]
Circulation_2: AttributeCreator [off]
    ATTR_TABLE = SET_TO SPACECAT1KEY = 020
    -> Building_Service_2_OUTPUT [off]
Mechanical_2: AttributeCreator [off]
    ATTR_TABLE = SET_TO SPACECAT1KEY = 030
    -> Building_Service_2_OUTPUT [off]
Unclassified_2: AttributeCreator [off]
    ATTR_TABLE = SET_TO SPACECAT1KEY = 000
    -> Building_Service_2_OUTPUT [off]
Building_Service_2_OUTPUT: Junction [off]
    -> DBO.SpaceClassificationLevel2 (writer GEODATABASE_SDE_4) [off]
    -> DBO.SpaceClassificationLevel2 (writer GEODATABASE_SDE_5) [off]
    -> DBO.SpaceClassificationLevel2 (writer GEODATABASE_SDE_6) [off]
DBO.SpaceClassificationLevel2 (writer GEODATABASE_SDE_4) [off]
    attributes: SPACECAT2ID char(5), DESCRIPTION char(255), SPACECAT1KEY char(5), OBJECTID integer
DBO.SpaceClassificationLevel2 (writer GEODATABASE_SDE_5)
    attributes: SPACECAT2ID char(5), DESCRIPTION char(255), SPACECAT1KEY char(5), OBJECTID integer
DBO.SpaceClassificationLevel2 (writer GEODATABASE_SDE_6)
    attributes: SPACECAT2ID char(5), DESCRIPTION char(255), SPACECAT1KEY char(5), OBJECTID integer

Bookmark: new interiorspace lookup
InteriorSpaceLookup (writer GEODATABASE_SDE_4)
    attributes: FLOORKEY char(200), SPACEID char(60), ROOMNUMBER char(30), DESCRIPTION char(50), ASSIGNMENTCOLLEGEKEY char(200), ASSIGNMENTSUBCOLLEGEKEY char(200), ASSIGNMENTDEPARTMENTKEY char(200), ASSIGNMENTKEY char(200)
InteriorSpaceLookup (writer GEODATABASE_SDE_5)
    attributes: FLOORKEY char(200), SPACEID char(60), ROOMNUMBER char(30), DESCRIPTION char(50), ASSIGNMENTCOLLEGEKEY char(200), ASSIGNMENTSUBCOLLEGEKEY char(200), ASSIGNMENTDEPARTMENTKEY char(200), ASSIGNMENTKEY char(200)
InteriorSpaceLookup (writer GEODATABASE_SDE_6)
    attributes: FLOORKEY char(200), SPACEID char(60), ROOMNUMBER char(30), DESCRIPTION char(50), ASSIGNMENTCOLLEGEKEY char(200), ASSIGNMENTSUBCOLLEGEKEY char(200), ASSIGNMENTDEPARTMENTKEY char(200), ASSIGNMENTKEY char(200)

Bookmark: doesn't change, don't update
DBO.Floor_Level (writer GEODATABASE_SDE_4) [off]
    attributes: FLOORCODE char(5), FLOORLEVEL integer, FLOORSHORTNAME char(50), FLOORLONGNAME char(100), OBJECTID integer
DBO.Floor_Level (writer GEODATABASE_SDE_5)
    attributes: FLOORCODE char(5), FLOORLEVEL integer, FLOORSHORTNAME char(50), FLOORLONGNAME char(100), OBJECTID integer
DBO.Floor_Level (writer GEODATABASE_SDE_6)
    attributes: FLOORCODE char(5), FLOORLEVEL integer, FLOORSHORTNAME char(50), FLOORLONGNAME char(100), OBJECTID integer

Bookmark: why is this broken all of a sudden?
DBO.Building: Junction
    -> DBO.Building (writer GEODATABASE_SDE_5)
    -> DBO.Building (writer GEODATABASE_SDE_6)
    -> Aggregator_2
DBO.Building (writer GEODATABASE_SDE_5)
    attributes: OBJECTID integer, BUILDINGID char(50), FACILITY_CODE char(4), ADA char(15), ADDRESS char(120), ASSIGNMENTKEY char(50), BUILDINGTYPEKEY char(50), BUILDINGMANAGER char(50), CAPACITY smallint, CONDITIONKEY char(50), DESCRIPTION char(255), FACILITYKEY char(50), FACILITYNAME char(255), FLOORCOUNT integer, GROSSAREA double, LONGNAME char(100), MAINTBY char(50), NETAREA double, OCCUPANCY smallint, OPERHOURSKEY char(50), OWNEDBY char(50), REPLCOST double, SHORTNAME char(25), URL char(255), YEARBUILT smallint, USABLEAREA double, ASSIGNABLEAREA double, PERCENTUSABLE double, PERCENTASSIGNABLE double, OCCUPANCYRATE double,
      VACANCYRATE double, DENSITY double, created_date date, created_user char(255), last_edited_date date, last_edited_user char(255), SHAPE.STArea() double, SHAPE.STLength() double
DBO.Building (writer GEODATABASE_SDE_6)
    attributes: OBJECTID integer, BUILDINGID char(50), FACILITY_CODE char(4), ADDRESS char(120), ASSIGNMENTKEY char(50), BUILDINGTYPEKEY char(50), CONDITIONKEY char(50), DESCRIPTION char(255), FACILITYKEY char(50), FACILITYNAME char(255), FLOORCOUNT integer, GROSSAREA double, LONGNAME char(100), MAINTBY char(50), NETAREA double, OWNEDBY char(50), REPLCOST double, SHORTNAME char(25), URL char(255), YEARBUILT smallint, USABLEAREA double, ASSIGNABLEAREA double, created_date date, created_user char(255), last_edited_date date, last_edited_user char(255), OUTLINETYPE char(50), STATUS char(50), PrimaryRoomTypeGroup char(50), PrimaryRoomTypeGroupSqft integer,
      ROOMCOUNT integer, CONSTRUCTION_OR_PURCHASE_COST integer, LAST_MAJOR_RENOVATION_DATE date, LAST_MAJOR_RENOVATION_COST integer, REGISTERED_HISTORIC_SITE char(50), DEPTS char(250), SITEKEY char(50), SHAPE.STArea() double, SHAPE.STLength() double
DBO.Building (writer GEODATABASE_SDE_4) [off]
    attributes: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

Bookmark: new floor lookup
FloorLookup (writer GEODATABASE_SDE_4) [off]
    attributes: BUILDINGKEY char(50), FLOORID char(50), FLOORSHORTNAME char(50), FLOORLONGNAME char(100), VERTORDER char(5)
FloorLookup (writer GEODATABASE_SDE_5)
    attributes: BUILDINGKEY char(50), FLOORID char(50), FLOORSHORTNAME char(50), FLOORLONGNAME char(100), VERTORDER char(5)
FloorLookup (writer GEODATABASE_SDE_6)
    attributes: BUILDINGKEY char(50), FLOORID char(50), FLOORSHORTNAME char(50), FLOORLONGNAME char(100), VERTORDER char(5)
