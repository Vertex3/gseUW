FME workspace gseBuildingDerive.fmw
Title: GizintaLoader
Description: First Beta release of Gizinta for FME
Usage: Add the xml file and other parameters
Requirements: test
History: 31/10/2013,support@Gizinta.com,First Draft
Legal terms conditions: This work is licensed under the Creative Commons Attribution-ShareAlike 3.0 Unported License.
Startup Python:
      import xml.dom.minidom
      import os
      import sys
      import time
      import fmeobjects

      ospath = FME_MacroValues['FME_MF_DIR']
      print ospath
      if ospath not in sys.path:
          sys.path.append(ospath)
      import gzfme

      ErrorUniqueID = "ErrorUniqueID"
      ErrorRequiredValue = "ErrorRequiredValue"
      ErrorValueMap = "ErrorValueMap"
      Errors = False

      debug = gzfme.setDebug(FME_MacroValues['gzDebug'])
      logger = fmeobjects.FMELogFile()
      gzfme.logger = logger
Shutdown Python:
      import fmeobjects, gzfme

      gzfme.shutdown(Errors,str(FME_MacroValues['IgnoreErrors']),FME_TotalFeaturesWritten,FME_MacroValues)

      del Errors
      del ErrorUniqueID
      del ErrorRequiredValue
      del ErrorValueMap
      del debug
      del logger
      gzfme.logger = None

Parameters:
- DestDataset_GEODATABASE_SDE = sde   # Destination Esri ArcSDE Geodatabase Dataset
- OUT_CONNECTION_FILE_GEODATABASE_SDE = C:\Apps\Gizinta\gseUW\ETL\serverConfig\GIS Staging.sde   # Connection File
- GizintaProject = C:\Apps\Gizinta\gseUW\ETL\config\bmBldgDerivePlaylist.xml   # Select the Gizinta Xml File to use
- SourceFieldQA = False   # Choose whether to perform QA on Source Fields
- TargetFieldQA = True   # Choose whether to perform QA on Target Fields
- IgnoreErrors = False   # Ignore Errors and continue
- SourceDatasetTypes = GDBDataset   # Enter the Gizinta Source Dataset Type
- SourceDataset_GEODATABASE_SDE = sde   # Source Esri ArcSDE Geodatabase Dataset
- gzDebug = False   # Enable gzDebug (True/False)
- LOG_FILE =   # Log File
- FEATURE_TYPES = Building_Point DBO.Building Building DBO.Building_Point   # Feature Types to Read

Readers:
- GEODATABASE_SDE_1: GEODATABASE_SDE from $(DestDataset_GEODATABASE_SDE)
- GEODATABASE_SDE_2: GEODATABASE_SDE from $(SourceDataset_GEODATABASE_SDE)

Writers:
- GEODATABASE_SDE_3: GEODATABASE_SDE to $(DestDataset_GEODATABASE_SDE)

Building (reader GEODATABASE_SDE_2)
    attributes: geodb_oid integer, OBJECTID integer, BUILDINGID char(4), FACILITYNO char(10), NAME char(255), IN_DATE date, LAST_USER char(30), SOURCEID char(30), SOURCEDWG char(60), Override blob, RuleID integer, GlobalID char(38), SHAPE.STArea() double, SHAPE.STLength() double
    -> AttributeExposer
AttributeExposer
    ATTR_LIST = fme_basename
    -> AttributeCopier
AttributeCopier
    ATTR_LIST = DRAWING,SOURCEDWG
    -> gseBuildingLoad_2
gseBuildingLoad_2
    OutputBuildings -> gzFieldCalculator
gzFieldCalculator
    AddFieldsValues_Output_1 -> Tester
Tester
    TEST_MODE = Automatic
    TEST_DESCRIPTION = ""
    BOOL_OP = OR
    TEST_CLAUSE = TEST @Value(fme_feature_type) = BuildingAgg
    PASSED -> AttributeCreator_6
    FAILED -> gzWriteData
AttributeCreator_6
    ATTR_LIST = fme_feature_type,Building
    -> gzWriteData
gzWriteData
    IgnoreErrors = False
    GroupBy = @Value(fme_feature_type)
    HASERRORS = HasErrors
    gzLogWriter -> gzLog (writer GEODATABASE_SDE_3)
    gzFeatureWriter -> Features (writer GEODATABASE_SDE_3)
    gzErrorWriter -> gzError (writer GEODATABASE_SDE_3)
gzLog (writer GEODATABASE_SDE_3)
    attributes: PROCNAME char(255), LOADTIME date, LOADNAME char(255), DATASET char(255), COMPLETED smallint, LOADUSER char(255), ACTIVEFLAG char(255)
Features (writer GEODATABASE_SDE_3)
gzError (writer GEODATABASE_SDE_3)
    attributes: PROCNAME char(255), SOURCENAME char(255), SRCIDFIELD char(255), SRCIDVAL char(255), DATASET char(255), REASON char(255), ERRUSER char(255), ERRTIME date, ACTIVEFLAG char(255)

FME custom transformer gseBuildingLoad

BuildingReader (input)
    -> Bufferer
Bufferer
    GROUP_BY = BUILDINGID
    INTERP_SEGMENTS = 8
    OFFSET = .01
    CAP_STYLE = None
    BUFFERED -> Intersector
Intersector
    DUPLICATE_Z_NODES = No
    GRP_BY = BUILDINGID
    SEPARATE_COLLINEAR_SEGMENTS = No
    PERFORM_SELF_INTERSECTION = No
    SEG_ATTR = _segments
    OV_ATTR = _overlaps
    INTERSECTED -> Generalizer
Generalizer
    ALG_TEXT = Douglas (Generalize)
    PRESERVE = No
    TOLERANCE = .05
    -> GeometryCoercer
GeometryCoercer
    CHECKZ = No
    KIND = fme_polygon
    COERCED -> GeometryFilter
GeometryFilter
    BREAK_AGG = Yes
    AREA -> Aggregator
Aggregator
    GROUP_BY = BUILDINGID
    MODE = Assemble One Level
    ACCUM_ATTRS_NAME = Yes
    SEP = ,
    AGGREGATE_TYPE = Homogeneous Collection (If Possible)
    ORDERED = No
    AGGREGATE -> AttributeCreator_5
    AGGREGATE -> InsidePointReplacer
AttributeCreator_5
    ATTR_LIST = fme_feature_type,BuildingAgg
    -> Tester
InsidePointReplacer
    INSIDEPOINT -> AttributeCreator_2
AttributeCreator_2
    ATTR_LIST = fme_feature_type,Building_Point
    -> Tester
Tester
    TEST_MODE = Automatic
    TEST_DESCRIPTION = ""
    BOOL_OP = OR
    TEST_CLAUSE = NUM_TEST @Value(BUILDINGID) > 0
    PASSED -> OutputBuildings (output)
OutputBuildings (output)

FME custom transformer gzFixCatwalks
Fix "catwalks" in source polygons from CAD. Typically for rooms inside of rooms and other inner polygons in CAD there are lines drawn so that room areas can be calculated. This transformer will remove those lines and other small self-intersections.

Parameters:
- Tolerance = 0.001   # Generalization tolerance
- UniqueIDName = SPACEID   # UniqueID field name for polygons
- Feature_Type = InteriorSpace_All   # Feature Type to process

INPUT (input)
    -> AttributeExposer
AttributeExposer
    ATTR_LIST = fme_feature_type,DRAWING,BUILDINGID,FLOORID
    -> Tester
Tester
    TEST_MODE = Automatic
    TEST_DESCRIPTION = ""
    BOOL_OP = OR
    TEST_CLAUSE = TEST @Value(fme_feature_type) = $(Feature_Type)
    PASSED -> Generalizer
    FAILED -> OUTPUT (output)
Generalizer
    ALG_TEXT = Douglas (Generalize)
    PRESERVE = No
    TOLERANCE = $(Tolerance)
    -> SelfIntersectChecker
SelfIntersectChecker
    SelfIntersecting -> SelfIntersector
    NotSelfIntersecting -> GeometryCoercer_2
SelfIntersector
    SEG_ATTR = _segments
    SELF_INTERSECTED -> AreaCalculator
AreaCalculator
    AREA_ATTR = _area
    AREA_TYPE = Plane Area
    MULT = 1
    -> TestFilter_2
TestFilter_2
    TEST_LIST = BOOL_OP,OR,COMPOSITE_TEST,<Unused>,TEST_CLAUSE,"TEST ""@Value(_area)"" >= ""1""",_area >= 1
    DEFAULT_VALUE = <UNFILTERED>
    _area >= 1 -> Aggregator
Aggregator
    GROUP_BY = $(UniqueIDName)
    SEP = ,
    CONTAIN_INDIVID_GEOMS = No
    ACCUM_ATTRS_NAME = Yes
    ORDERED = No
    AGGREGATE -> GeometryCoercer_2
GeometryCoercer_2
    CHECKZ = No
    KIND = fme_polygon
    COERCED -> SelfIntersectChecker_2
SelfIntersectChecker_2
    NotSelfIntersecting -> OUTPUT (output)
    SelfIntersecting -> Logger_SelfIntersecting
OUTPUT (output)
Logger_SelfIntersecting
    MESSAGE = Feature is self-intersecting:
    MAXFEATS = 100
    MAXCOORDS = 20

FME custom transformer gzTiltRooms
Tilt Rooms in floorplans to create a pseudo-isometric view of the rooms and floors

Parameters:
- pBUILDINGID = 1327   # Enter the Building Identifier
- pFLOORID = 1327_01   # Enter the FacFloor Number

INPUT (input)
    -> DuplicateRemover
    -> FeatureMerger_2 [input 1]
    -> DuplicateRemover_2
DuplicateRemover_2
    KEYATTR = $(pBUILDINGID)
    UNIQUE -> BldgReader
BldgReader: FeatureReader
    GEODATABASE_SDE_RESOLVE_SUBTYPE_NAMES = yes
    GEODATABASE_SDE_SPLIT_COMPLEX_EDGES = no
    FEATURETYPES = DBO.Building_Outline_Tilt
    GEODATABASE_SDE_VERSION = SDE.DEFAULT
    GEODATABASE_SDE_TRANSLATE_SPATIAL_DATA_ONLY = no
    GEODATABASE_SDE_CONNECTION = Connection File
    COMBINE_GEOM = Keep result geometry only
    GEODATABASE_SDE_VERSION_TYPE = Connect using a Transactional Version
    COMBINE_ATTRS = Keep result attributes only
    GEODATABASE_SDE_REMOVE_TABLE_QUALIFIER = YES
    GEODATABASE_SDE_IGNORE_RELATIONSHIP_INFO = yes
    GEODATABASE_SDE_WHERE = BUILDINGID=$(pBUILDINGID)
    SUPPORTED_SPATIAL_INTERACTIONS = ENVELOPE_INTERSECT%INTERSECTS%CONTAINS%CROSSES%DISJOINT%EQUALS%OVERLAPS%TOUCHES%WITHIN
    DATASET = sde
    GEODATABASE_SDE_TABLELIST = DBO.Building_Outline_Tilt
    GEODATABASE_SDE_SPLIT_MULTI_PART_ANNOS = no
    ATTRIBUTES = DBO.Building_Outline_Tilt,"geodb_oid,OBJECTID,BUILDINGID,HULLROT,BLDGHEIGHT,SPACING,MARGIN,XCENTER,YCENTER,SOURCEID,SOURCEDWG,IN_DATE,LAST_USER,GlobalID,SHAPE.STArea(),SHAPE.STLength()"
    GEODATABASE_SDE_RESOLVE_DOMAINS = no
    FORMAT = GEODATABASE_SDE
    GEODATABASE_SDE_CONNECTION_FILE = $(FME_MF_DIR)GIS Production.sde
    GEODATABASE_SDE_IGNORE_NETWORK_INFO = yes
    DBO.Building_Outline_Tilt -> BoundsExtractor_2
BoundsExtractor_2
    YMIN = _ymin
    ZMIN = _zmin
    XMIN = _xmin
    XMAX = _xmax
    ZMAX = _zmax
    YMAX = _ymax
    -> FeatureMerger_2 [input 2]
FeatureMerger_2
    PROCESS_DUPS = No
    MERGE_TYPE = Attributes Only
    SUPPLIERS_FIRST = No
    JOIN_KEYS = @Value(BUILDINGID) $(pBUILDINGID)
    SUPPLIER_PREFIX_DUMMY = YES
    MERGED -> FeatureMerger_3 [input 1]
DuplicateRemover
    KEYATTR = $(pBUILDINGID)
    UNIQUE -> FloorsReader
FloorsReader: FeatureReader
    GEODATABASE_SDE_RESOLVE_SUBTYPE_NAMES = yes
    GEODATABASE_SDE_SPLIT_COMPLEX_EDGES = no
    FEATURETYPES = DBO.Active_Floor
    GEODATABASE_SDE_VERSION = SDE.DEFAULT
    GEODATABASE_SDE_TRANSLATE_SPATIAL_DATA_ONLY = no
    GEODATABASE_SDE_CONNECTION = Connection File
    COMBINE_GEOM = In case of conflict, keep aggregate of INITIATOR and result geometry
    GEODATABASE_SDE_VERSION_TYPE = Connect using a Transactional Version
    COMBINE_ATTRS = In case of conflict, keep result attributes
    GEODATABASE_SDE_REMOVE_TABLE_QUALIFIER = NO
    GEODATABASE_SDE_IGNORE_RELATIONSHIP_INFO = yes
    GEODATABASE_SDE_WHERE = BUILDINGID=$(pBUILDINGID)
    SUPPORTED_SPATIAL_INTERACTIONS = ENVELOPE_INTERSECT%INTERSECTS%CONTAINS%CROSSES%DISJOINT%EQUALS%OVERLAPS%TOUCHES%WITHIN
    DATASET = sde
    GEODATABASE_SDE_TABLELIST = DBO.Active_Floor
    GEODATABASE_SDE_SPLIT_MULTI_PART_ANNOS = no
    ATTRIBUTES = DBO.Active_Floor,"geodb_oid,OBJECTID,BUILDINGID,FLOOR,FLOORID,DWG_NAME,INTERIORSPACE,FLOORPLANLINE,SCHELEV,ALTITUDE,GlobalID"
    GEODATABASE_SDE_RESOLVE_DOMAINS = no
    FORMAT = GEODATABASE_SDE
    GEODATABASE_SDE_CONNECTION_FILE = $(FME_MF_DIR)GIS Production.sde
    GEODATABASE_SDE_IGNORE_NETWORK_INFO = yes
    DBO.Active_Floor -> AttributeCopier_3
AttributeCopier_3
    ATTR_LIST = STACKLEVEL,SCHELEV
    -> FeatureMerger_3 [input 2]
FeatureMerger_3
    PROCESS_DUPS = No
    MERGE_TYPE = Attributes Only
    SUPPLIERS_FIRST = No
    JOIN_KEYS = @Value(FLOORID) $(pFLOORID)
    SUPPLIER_PREFIX_DUMMY = YES
    MERGED -> ExpressionEvaluator_2
ExpressionEvaluator_2
    VAL_ATTR = CALCULATED_ROTATION
    EXPRESSION = @Value(HULLROT) + 15.0
    -> Rotator
Rotator
    YORIG = @Value(_ymin)
    ANGLE = @Value(CALCULATED_ROTATION)
    XORIG = @Value(_xmin)
    ROTATED -> Y_Base
Y_Base: ExpressionEvaluator
    VAL_ATTR = _yBase
    EXPRESSION = @Value(_ymin) + (@Value(SPACING) * @Value(STACKLEVEL))
    -> tilt_Space
tilt_Space: ExpressionEvaluator
    VAL_ATTR = _tiltSpace
    EXPRESSION = @Value(BLDGHEIGHT) / (@Value(SPACING)+0.00001)
    -> Chopper
Chopper
    MAX = 1
    CHOPPED -> CoordinateExtractor
CoordinateExtractor
    Y_ATTR = _y
    X_ATTR = _x
    Z_DEFAULT = -9999
    Z_ATTR = _z
    IND = 0
    -> tilt_y
tilt_y: ExpressionEvaluator
    VAL_ATTR = _tiltY
    EXPRESSION = @Value(_yBase) + ((@Value(_y) - @Value(_ymin)) / @Value(_tiltSpace)) * (1 - @Value(MARGIN))
    -> 2DPointReplacer
2DPointReplacer
    XVALATTR = @Value(_x)
    YVALATTR = @Value(_tiltY)
    POINT -> PointConnector
PointConnector
    BREAKATTR = FACROOM
    POLYGON -> GeometryCoercer_2
    LINE -> GeometryCoercer_2
GeometryCoercer_2
    CHECKZ = No
    KIND = fme_polygon
    COERCED -> SliverRemover_2
SliverRemover_2
    REPAIR_METHOD = Longest Boundary
    REPAIRED -> OUTPUT (output)
OUTPUT (output)

FME custom transformer gzBuildingAngle

Parameters:
- BUILDINGID =   # Enter the Building ID

INPUT (input)
    -> Chopper_2
    -> FeatureMerger_3 [input 1]
Chopper_2
    MAX = 2
    CHOPPED -> LengthCalculator_2
LengthCalculator_2
    LEN_ATTR = _length
    MULT = 1
    DIM = 2
    -> StatisticsCalculator_2
StatisticsCalculator_2
    STATS_ATTR = _length
    PASS_THROUGH = Yes
    MAX_ATTR = _max
    RANGE_ATTR = _range
    SUM_ATTR = _sum
    COUNT_ATTR = _count
    NUMERIC_ATTR = _numeric_count
    STDEV_ATTR = _stdev
    MODE_ATTR = _mode
    MEDIAN_ATTR = _median
    MIN_ATTR = _min
    MEAN_ATTR = _mean
    STATISTICS -> TestFilter_6
TestFilter_6
    TEST_LIST = BOOL_OP,OR,COMPOSITE_TEST,<Unused>,TEST_CLAUSE,"TEST ""@Value(_length)"" = ""@Value(_max)""",_length = _max
    DEFAULT_VALUE = <UNFILTERED>
    _length = _max -> CoordinateExtractor_4
CoordinateExtractor_4
    Y_ATTR = _y1
    X_ATTR = _x1
    Z_DEFAULT = -9999
    Z_ATTR = _z
    IND = 0
    -> CoordinateExtractor_6
CoordinateExtractor_6
    Y_ATTR = _y2
    X_ATTR = _x2
    Z_DEFAULT = -9999
    Z_ATTR = _z
    IND = 1
    -> TestFilter_4
TestFilter_4
    TEST_LIST = BOOL_OP,OR,COMPOSITE_TEST,<Unused>,TEST_CLAUSE,"TEST ""@Value(_y2)"" >= ""@Value(_y1)""",_y2 >= _y1
    DEFAULT_VALUE = <UNFILTERED>
    _y2 >= _y1 -> ExpressionEvaluator_7
    <UNFILTERED> -> ExpressionEvaluator_4
Note: Calculate angle of the longest side
ExpressionEvaluator_7
    VAL_ATTR = _angle
    EXPRESSION = @atan2(@Value(_x1)-@Value(_x2),@Value(_y1)-@Value(_y2))*180.0/(22/7.0)
    -> ExpressionEvaluator_8
ExpressionEvaluator_4
    VAL_ATTR = _angle
    EXPRESSION = @atan2(@Value(_x2)-@Value(_x1),@Value(_y2)-@Value(_y1))*180.0/(22/7.0)
    -> ExpressionEvaluator_8
ExpressionEvaluator_8
    VAL_ATTR = _angle
    EXPRESSION = @Value(_angle) + 90.0
    -> TestFilter_5
TestFilter_5
    TEST_LIST = BOOL_OP,OR,COMPOSITE_TEST,<Unused>,TEST_CLAUSE,"TEST ""@Value(_angle)"" > ""180.0""",_angle > 180.0
    DEFAULT_VALUE = <UNFILTERED>
    _angle > 180.0 -> ExpressionEvaluator_10
    <UNFILTERED> -> Sorter_2
ExpressionEvaluator_10
    VAL_ATTR = _angle
    EXPRESSION = @Value(_angle) -180.0
    -> Sorter_2
Sorter_2
    SORT_PARM = _length NUMERIC DESCENDING
    SORTED -> FeatureMerger_3 [input 2]
FeatureMerger_3
    BUILD_INCOMPLETE = No
    PROCESS_DUPS = No
    MERGE_TYPE = Attributes Only
    REFERATTR = $(BUILDINGID)
    REFEEATTR = $(BUILDINGID)
    COMPLETE -> GeometryExtractor_2
GeometryExtractor_2
    ATTR = _geometry
    KIND_LONG = FME Binary
    -> CenterOfGravityReplacer
CenterOfGravityReplacer
    CENTEROFGRAVITY -> CoordinateExtractor_3
CoordinateExtractor_3
    Y_ATTR = YCENTER
    X_ATTR = XCENTER
    Z_DEFAULT = -9999
    Z_ATTR = _z
    IND = 0
    -> GeometryReplacer
GeometryReplacer
    ATTR = _geometry
    KIND_LONG = FME Binary
    -> AttributeCreator
Note: Calculate X and Y Center Point
AttributeCreator
    ATTR_LIST = MODANGLE,0,SPACING,50,MARGIN,.2,HULLROT,@Value(_angle)
    -> OUTPUT (output)
OUTPUT (output)

FME custom transformer SelfIntersectChecker
Separates self-intersecting features from the rest of input. This custom transformer does not change the geometry of self-intersecting features. If you want to remove self-intersections, try the " SelfIntersector " transformer.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Input (input)
    -> PartCounter
PartCounter
    COUNT_ATTR = _part_count1
    RECURSIVE_PARAM = No
    -> COUNTER
COUNTER: Counter
    SCOPE = Local
    START = 0
    DOMAIN = counter
    CNT_ATTR = _selfID
    -> GeometryExtractor
GeometryExtractor
    OGCVERSION = 1.2
    ATTR = _geometry
    KIND_LONG = OGC Well Known Text
    -> SelfIntersector
SelfIntersector
    SEG_ATTR = _segments
    SELF_INTERSECTED -> DuplicateRemover
DuplicateRemover
    KEYATTR = _selfID
    UNIQUE -> TESTER
TESTER: Tester
    TEST_MODE = NUMERIC
    BOOL_OP = OR
    TEST_LIST = &_segments,>,1
    TEST_CLAUSE = TEST @Value(_segments) > 1
    FAILED -> PartCounter_2
    PASSED -> GeometryReplacer
PartCounter_2
    COUNT_ATTR = _part_count2
    RECURSIVE_PARAM = No
    -> TESTER_2
TESTER_2: Tester
    TEST_MODE = Automatic
    BOOL_OP = OR
    TEST_LIST = &_part_count1,=,&_part_count2
    TEST_CLAUSE = TEST @Value(_part_count1) = @Value(_part_count2)
    PASSED -> ATTRIBUTEREMOVER
    FAILED -> GeometryReplacer
ATTRIBUTEREMOVER: AttributeRemover
    REMOVE_ATTRS = _selfID,_geometry,_segments
    -> NotSelfIntersecting (output)
NotSelfIntersecting (output)
GeometryReplacer
    ATTR = _geometry
    KIND_LONG = OGC Well Known Text
    -> ATTRIBUTEREMOVER_2
ATTRIBUTEREMOVER_2: AttributeRemover
    REMOVE_ATTRS = _selfID,_geometry,_segments
    -> SelfIntersecting (output)
SelfIntersecting (output)

FME custom transformer gzAggregateLines
Clean geometries and Aggregate Floorplan lines into _Optimized features

INPUT (input)
    -> CoordinateCounter
CoordinateCounter
    CNT_ATTR = _coordcount
    -> LengthCalculator_2
LengthCalculator_2
    LEN_ATTR = _length
    MULT = 1
    DIM = 2
    -> TestFilter_6
TestFilter_6
    TEST_LIST:
      BOOL_OP,AND,COMPOSITE_TEST,<Unused>,TEST_CLAUSE,"TEST ""@Value(_coordcount)"" >= ""2""
      TEST ""@Value(_length)"" >= "".001""",2pts & length > .01
    DEFAULT_VALUE = <UNFILTERED>
    2pts & length > .01 -> SelfIntersectChecker
SelfIntersectChecker
    NotSelfIntersecting -> GeometryCoercer
    SelfIntersecting -> SelfIntersector
SelfIntersector
    SEG_ATTR = _segments
    SELF_INTERSECTED -> GeometryCoercer
GeometryCoercer
    KIND = fme_line
    COERCED -> Aggregator_2
Aggregator_2
    GROUP_BY = FLOORID
    SEP = ,
    CONTAIN_INDIVID_GEOMS = No
    ACCUM_ATTRS_NAME = Yes
    ORDERED = No
    AGGREGATE -> OUTPUT (output)
OUTPUT (output)
