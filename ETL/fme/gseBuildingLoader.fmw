FME workspace gseBuildingLoader.fmw
Title: GizintaLoader
Description: First Beta release of Gizinta for FME
Usage: Add the xml file and other parameters
Requirements: test
History: 31/10/2013,support@Gizinta.com,First Draft
Legal terms conditions: This work is licensed under the Creative Commons Attribution-ShareAlike 3.0 Unported License.
Startup Python:
      import xml.dom.minidom
      import os
      import sys
      import time
      import fmeobjects

      ospath = FME_MacroValues['FME_MF_DIR']
      print ospath
      if ospath not in sys.path:
          sys.path.append(ospath)
      import gzfme

      ErrorUniqueID = "ErrorUniqueID"
      ErrorRequiredValue = "ErrorRequiredValue"
      ErrorValueMap = "ErrorValueMap"
      Errors = False

      debug = gzfme.setDebug(FME_MacroValues['gzDebug'])
      logger = fmeobjects.FMELogFile()
      gzfme.logger = logger
Shutdown Python:
      import fmeobjects, gzfme

      gzfme.shutdown(Errors,str(FME_MacroValues['IgnoreErrors']),FME_TotalFeaturesWritten,FME_MacroValues)

      del Errors
      del ErrorUniqueID
      del ErrorRequiredValue
      del ErrorValueMap
      del debug
      del logger
      gzfme.logger = None

Parameters:
- DestDataset_GEODATABASE_SDE = sde   # Destination Esri ArcSDE Geodatabase Dataset
- OUT_CONNECTION_FILE_GEODATABASE_SDE = C:\Apps\Gizinta\gseUW\ETL\serverConfig\GIS Staging.sde   # Connection File
- GizintaProject = C:\Apps\Gizinta\gseUW\ETL\config\bldgLoadPlaylist.xml   # Select the Gizinta Xml File to use
- SourceFieldQA = False   # Choose whether to perform QA on Source Fields
- TargetFieldQA = True   # Choose whether to perform QA on Target Fields
- IgnoreErrors = False   # Ignore Errors and continue
- SourceDatasetTypes = CADDataset   # Enter the Gizinta Source Dataset Type
- gzDebug = False   # Enable gzDebug (True/False)
- LOG_FILE =   # Log File
- SourceCoordinateSystem = EPSG:2285   # Source Coordinate System
- SourceDataset_ESRIMSD = C:\Vault_Mirror\CADVault\ARZ-Arizona\6327-RPA-SALT RIV PRIMATE FAC\*Outline.dwg   # Source Autodesk AutoCAD DWG/DXF File(s)
- FEATURE_TYPES_READ = FloorPageTemplate Building_Outline_Tilt   # Feature Types to Read
- SourceDataset_GEODATABASE_SDE = sde   # Source Esri ArcSDE Geodatabase Dataset

Readers:
- ESRIMSD_1: ESRIMSD from $(SourceDataset_ESRIMSD)
- GEODATABASE_SDE_1: GEODATABASE_SDE from $(SourceDataset_GEODATABASE_SDE)

Writers:
- GEODATABASE_SDE_2: GEODATABASE_SDE to $(DestDataset_GEODATABASE_SDE)

Building_Roof (reader ESRIMSD_1)
    attributes: FACNUM char(254)
    -> AttributeExposer
AttributeExposer
    ATTR_LIST = fme_basename,fme_feature_type,FACNUM,autocad_source_filename
    -> Tester
Tester
    TEST_DESCRIPTION = ""
    TEST_MODE = Automatic
    TEST_CLAUSE = TEST $(FEATURE_TYPES_READ) CONTAINS @Value(fme_feature_type)
    BOOL_OP = OR
    PASSED -> gzFieldCalculator
gzFieldCalculator
    AddFieldsValues_Output_1 -> bldg
bldg: AttributeExposer
    ATTR_LIST = BUILDINGID
    -> gzLocalRot
gzLocalRot: gzBuildingOutline
    FACNUM = @Value(FACNUM)
    BUILDINGID = @Value(BUILDINGID)
    -> AttributeRenamer
AttributeRenamer
    ATTR_LIST = CALCROT,LOCALROT,
    -> Reprojector
Reprojector
    SOURCE = $(SourceCoordinateSystem)
    RASTER_CELL_SIZE = Preserve Cells
    DEST = EPSG:3857
    INTERPOLATION_TYPE_NAME = Nearest Neighbor
    STROKE_ARCS = Yes
    REPROJECTED -> TestFilter_2
    REPROJECTED -> Reprojector_Reprojected
TestFilter_2
    DEFAULT_VALUE = <UNFILTERED>
    TEST_LIST = BOOL_OP,OR,COMPOSITE_TEST,<Unused>,TEST_CLAUSE,"TEST @Value(fme_feature_type) = FloorPageTemplate",FloorPageTemplate
    FloorPageTemplate -> AttributeCreator_2
Note: Special Calculations for Outline attributes
AttributeCreator_2
    ATTR_LIST = fme_feature_type,FloorPageTemplate
    -> gzBuildingOutlineTilt
gzBuildingOutlineTilt
    FACNUM = @Value(FACNUM)
    BUILDINGID = @Value(BUILDINGID)
    -> gzSourceTargetQA
gzSourceTargetQA
    SourceTargetQA_Output_1 -> gzWriteData
gzWriteData
    GroupBy = @Value(BUILDINGID)
    HASERRORS = @Value(HasErrors)
    IgnoreErrors = False
    gzLogWriter -> gzLog (writer GEODATABASE_SDE_2)
    gzFeatureWriter -> DBO.Building_Outline_Tilt (writer GEODATABASE_SDE_2)
    gzErrorWriter -> gzError (writer GEODATABASE_SDE_2)
gzLog (writer GEODATABASE_SDE_2)
    attributes: PROCNAME char(255), LOADTIME date, LOADNAME char(255), DATASET char(255), COMPLETED smallint, LOADUSER char(255), ACTIVEFLAG char(255)
DBO.Building_Outline_Tilt (writer GEODATABASE_SDE_2)
    attributes: geodb_oid integer, OBJECTID integer, SITEID char(60), BUILDINGID char(60), CALCROT double, SOURCEID char(30), SOURCEDWG char(60), LASTUPDATE date, LASTEDITOR char(30), BLDGNAME char(100), SHAPE.STArea() double, SHAPE.STLength() double
gzError (writer GEODATABASE_SDE_2)
    attributes: PROCNAME char(255), SOURCENAME char(255), SRCIDFIELD char(255), SRCIDVAL char(255), DATASET char(255), REASON char(255), ERRUSER char(255), ERRTIME date, ACTIVEFLAG char(255)
Reprojector_Reprojected: Inspector [off]
CenterPointReplacer
    CENTERPOINT -> AttributeCreator
Note: no longer used. Building Points from siteplan
AttributeCreator
    ATTR_LIST = fme_feature_type,Building_Outline_Point

FME custom transformer gzCalculateRotation

Parameters:
- SourceCoordinateSystem = EPSG:2285   # Source Coordinate System

INPUT (input)
    -> AttributeCreator_7
AttributeCreator_7
    ATTR_LIST = WORLD,World
    -> AttributeFilter
AttributeFilter
    ATTR_NAME = text_line_number
    ATTR_VALUES = <BLANK>,<UNFILTERED>,1,2
    1 -> AttributeSplitter1
    2 -> AttributeSplitter2
AttributeSplitter1
    DROP_EMPTY_PARTS = No
    ATTR_NAME = text_line_data
    TRIM_OPTION = None
    LIST_NAME = _pts
    DELIMITER = " "
    -> AttributeSplitter_1
    -> AttributeSplitter_2
AttributeSplitter_1
    DROP_EMPTY_PARTS = No
    ATTR_NAME = _pts{0}
    TRIM_OPTION = Both
    LIST_NAME = _pt
    DELIMITER = ,
    -> AttributeCreator_1
AttributeCreator_1
    ATTR_LIST = x1,@Value(_pt{0}),y1,@Value(_pt{1})
    -> 2DPointAdder_1
2DPointAdder_1
    YVALATTR = @Value(y1)
    XVALATTR = @Value(x1)
    -> PointConnector
AttributeSplitter_2
    DROP_EMPTY_PARTS = No
    ATTR_NAME = _pts{1}
    TRIM_OPTION = Both
    LIST_NAME = _pt2
    DELIMITER = ,
    -> AttributeCreator_2
AttributeCreator_2
    ATTR_LIST = x2,@Value(_pt2{0}),y2,@Value(_pt2{1})
    -> 2DPointAdder_2
2DPointAdder_2
    YVALATTR = @Value(y2)
    XVALATTR = @Value(x2)
    -> PointConnector_2
AttributeSplitter2
    DROP_EMPTY_PARTS = No
    ATTR_NAME = text_line_data
    TRIM_OPTION = None
    LIST_NAME = _pts
    DELIMITER = " "
    -> AttributeSplitter_4
    -> AttributeSplitter_3
AttributeSplitter_3
    DROP_EMPTY_PARTS = No
    ATTR_NAME = _pts{0}
    TRIM_OPTION = Both
    LIST_NAME = _pt
    DELIMITER = ,
    -> AttributeCreator_3
AttributeCreator_3
    ATTR_LIST = x3,@Value(_pt{0}),y3,@Value(_pt{1})
    -> 2DPointAdder_3
2DPointAdder_3
    YVALATTR = @Value(y3)
    XVALATTR = @Value(x3)
    -> PointConnector
PointConnector
    LINE -> CoordinateExtractor
    LINE -> PointConnector_LINE
PointConnector_LINE: Inspector
CoordinateExtractor
    Z_ATTR = _z
    Y_ATTR = _y1
    IND = 0
    Z_DEFAULT = -9999
    X_ATTR = _x1
    -> CoordinateExtractor_2
CoordinateExtractor_2
    Z_ATTR = _z
    Y_ATTR = _y2
    IND = 1
    Z_DEFAULT = -9999
    X_ATTR = _x2
    -> ExpressionEvaluator1
ExpressionEvaluator1
    EXPRESSION = (@atan2((@Value(_y2)-@Value(_y1)),(@Value(_x2)-@Value(_x1))))*180.0/(22/7.0)
    VAL_ATTR = rot1
    -> FeatureMerger_3 [input 1]
AttributeSplitter_4
    DROP_EMPTY_PARTS = No
    ATTR_NAME = _pts{1}
    TRIM_OPTION = Both
    LIST_NAME = _pt2
    DELIMITER = ,
    -> AttributeCreator_4
AttributeCreator_4
    ATTR_LIST = x4,@Value(_pt2{0}),y4,@Value(_pt2{1})
    -> 2DPointAdder_4
2DPointAdder_4
    YVALATTR = @Value(y4)
    XVALATTR = @Value(x4)
    -> PointConnector_2
PointConnector_2
    LINE -> Reprojector_2
    LINE -> PointConnector_2_LINE
Reprojector_2
    SOURCE = $(SourceCoordinateSystem)
    RASTER_CELL_SIZE = Preserve Cells
    DEST = EPSG:3857
    INTERPOLATION_TYPE_NAME = Nearest Neighbor
    STROKE_ARCS = Yes
    REPROJECTED -> CoordinateExtractor_3
CoordinateExtractor_3
    Z_ATTR = _z
    Y_ATTR = _y1
    IND = 0
    Z_DEFAULT = -9999
    X_ATTR = _x1
    -> CoordinateExtractor_4
CoordinateExtractor_4
    Z_ATTR = _z
    Y_ATTR = _y2
    IND = 1
    Z_DEFAULT = -9999
    X_ATTR = _x2
    -> ExpressionEvaluator2
ExpressionEvaluator2
    EXPRESSION = (@atan2((@Value(_y2)-@Value(_y1)),(@Value(_x2)-@Value(_x1))))*180.0/(22/7.0)
    VAL_ATTR = rot2
    -> FeatureMerger_3 [input 2]
FeatureMerger_3
    JOIN_KEYS = @Value(WORLD) @Value(WORLD)
    IGNORE_NULLS = Yes
    MERGE_TYPE = Attributes Only
    SUPPLIERS_FIRST = No
    PROCESS_DUPS = No
    SUPPLIER_PREFIX_DUMMY = YES
    MERGED -> AttributeCreator
AttributeCreator
    ATTR_LIST = CALCROT,@Evaluate(@Value(rot2)-@Value(rot1)),WORLDFILE,@Value(text_line_data)
    -> ExpressionEvaluator_8
ExpressionEvaluator_8
    EXPRESSION = @Value(CALCROT) + 90.0
    VAL_ATTR = _angle
    -> TestFilter_5
TestFilter_5
    DEFAULT_VALUE = <UNFILTERED>
    TEST_LIST = BOOL_OP,OR,COMPOSITE_TEST,<Unused>,TEST_CLAUSE,"TEST ""@Value(CALCROT)"" > ""180.0""",_angle > 180.0
    _angle > 180.0 -> ExpressionEvaluator_10
    <UNFILTERED> -> AttributeRemover
ExpressionEvaluator_10
    EXPRESSION = @Value(CALCROT) -180.0
    VAL_ATTR = _angle
    -> AttributeRemover
AttributeRemover
    REMOVE_ATTRS = text_line_data,x1,y1,x2,y2,x3,y3,x4,y4,rot1,rot2,_list{0},_pt{0},_pt2{0},_list{1},_pt{1},_pt2{1}
    -> OUTPUT (output)
    -> AttributeCreator_OUTPUT
OUTPUT (output)
AttributeCreator_OUTPUT: Inspector
PointConnector_2_LINE: Inspector
Reprojector
    SOURCE = $(SourceCoordinateSystem)
    RASTER_CELL_SIZE = Preserve Cells
    DEST = EPSG:3857
    INTERPOLATION_TYPE_NAME = Nearest Neighbor
    STROKE_ARCS = Yes

FME custom transformer gzTiltRooms
Tilt Rooms in floorplans to create a pseudo-isometric view of the rooms and floors

Parameters:
- pFACNUM =   # Enter the Building Identifier
- pFacFloor =   # Enter the FacFloor Number

INPUT (input)
    -> DuplicateRemover
    -> FeatureMerger_2 [input 1]
    -> DuplicateRemover_2
DuplicateRemover_2
    KEYATTR = $(pFACNUM)
    UNIQUE -> BldgReader
BldgReader: FeatureReader
    GEODATABASE_SDE_VERSION_TYPE = Connect using a Transactional Version
    COMBINE_GEOM = Keep result geometry only
    GEODATABASE_SDE_IGNORE_RELATIONSHIP_INFO = yes
    FEATURETYPES = DBO.Building_Outline
    COMBINE_ATTRS = Keep result attributes only
    SUPPORTED_SPATIAL_INTERACTIONS = ENVELOPE_INTERSECT%ENVELOPE_INTERSECT%INTERSECTS%CONTAINS%CROSSES%DISJOINT%EQUALS%OVERLAPS%TOUCHES%WITHIN
    GEODATABASE_SDE_TABLELIST = DBO.Building_Outline
    GEODATABASE_SDE_SPLIT_MULTI_PART_ANNOS = no
    GEODATABASE_SDE_WHERE = FACNUM=@Value(FACNUM)
    GEODATABASE_SDE_RESOLVE_SUBTYPE_NAMES = yes
    GEODATABASE_SDE_CONNECTION = Connection File
    GEODATABASE_SDE_VERSION = SDE.DEFAULT
    GEODATABASE_SDE_IGNORE_NETWORK_INFO = yes
    FORMAT = GEODATABASE_SDE
    GEODATABASE_SDE_SPLIT_COMPLEX_EDGES = no
    GEODATABASE_SDE_RESOLVE_DOMAINS = no
    GEODATABASE_SDE_TRANSLATE_SPATIAL_DATA_ONLY = no
    GEODATABASE_SDE_CONNECTION_FILE = $(FME_MF_DIR)GIS Production.sde
    GEODATABASE_SDE_REMOVE_TABLE_QUALIFIER = NO
    ATTRIBUTES = DBO.Building_Outline,"geodb_oid,OBJECTID,FACNUM,HULLROT,BLDGHEIGHT,MODANGLE,SPACING,MARGIN,XCENTER,YCENTER,SHAPE.STArea(),SHAPE.STLength()"
    DATASET = sde
    DBO.Building_Outline -> BoundsExtractor_2
BoundsExtractor_2
    YMAX = _ymax
    XMAX = _xmax
    XMIN = _xmin
    YMIN = _ymin
    ZMIN = _zmin
    ZMAX = _zmax
    -> FeatureMerger_2 [input 2]
FeatureMerger_2
    JOIN_KEYS = @Value(FACNUM) @Value(FACNUM)
    IGNORE_NULLS = Yes
    MERGE_TYPE = Attributes Only
    SUPPLIERS_FIRST = No
    PROCESS_DUPS = No
    SUPPLIER_PREFIX_DUMMY = YES
    MERGED -> FeatureMerger_3 [input 1]
DuplicateRemover
    KEYATTR = $(pFACNUM)
    UNIQUE -> FloorsReader
FloorsReader: FeatureReader
    GEODATABASE_SDE_VERSION_TYPE = Connect using a Transactional Version
    COMBINE_GEOM = In case of conflict, keep aggregate of INITIATOR and result geometry
    GEODATABASE_SDE_IGNORE_RELATIONSHIP_INFO = yes
    FEATURETYPES = DBO.Active_Floor
    COMBINE_ATTRS = In case of conflict, keep result attributes
    SUPPORTED_SPATIAL_INTERACTIONS = ENVELOPE_INTERSECT%INTERSECTS%CONTAINS%CROSSES%DISJOINT%EQUALS%OVERLAPS%TOUCHES%WITHIN
    GEODATABASE_SDE_TABLELIST = DBO.Active_Floor
    GEODATABASE_SDE_SPLIT_MULTI_PART_ANNOS = no
    GEODATABASE_SDE_RESOLVE_SUBTYPE_NAMES = yes
    GEODATABASE_SDE_CONNECTION = Connection File
    GEODATABASE_SDE_VERSION = SDE.DEFAULT
    GEODATABASE_SDE_IGNORE_NETWORK_INFO = yes
    FORMAT = GEODATABASE_SDE
    GEODATABASE_SDE_SPLIT_COMPLEX_EDGES = no
    GEODATABASE_SDE_RESOLVE_DOMAINS = no
    GEODATABASE_SDE_TRANSLATE_SPATIAL_DATA_ONLY = no
    GEODATABASE_SDE_CONNECTION_FILE = $(FME_MF_DIR)GIS Production.sde
    GEODATABASE_SDE_REMOVE_TABLE_QUALIFIER = NO
    ATTRIBUTES = DBO.Active_Floor,"geodb_oid,OBJECTID,FACNUM,FLOOR,FACFLOOR,DWG_NAME,INTERIORSPACE,FLOORPLANLINE,SCHELEV,ALTITUDE,GlobalID"
    DATASET = sde
    DBO.Active_Floor -> AttributeCopier_3
AttributeCopier_3
    ATTR_LIST = STACKLEVEL,SCHELEV
    -> FeatureMerger_3 [input 2]
FeatureMerger_3
    JOIN_KEYS = @Value(FACFLOOR) @Value(FACFLOOR)
    IGNORE_NULLS = Yes
    MERGE_TYPE = Attributes Only
    SUPPLIERS_FIRST = No
    PROCESS_DUPS = No
    SUPPLIER_PREFIX_DUMMY = YES
    MERGED -> ExpressionEvaluator_2
ExpressionEvaluator_2
    EXPRESSION = @Value(MODANGLE) + @Value(HULLROT) + 15.0
    VAL_ATTR = CALCULATED_ROTATION
    -> Rotator
Rotator
    ANGLE = @Value(CALCULATED_ROTATION)
    XORIG = 0
    YORIG = 0
    ROTATED -> Y_Base
Y_Base: ExpressionEvaluator
    EXPRESSION = @Value(_ymin) + (@Value(SPACING) * @Value(STACKLEVEL))
    VAL_ATTR = _yBase
    -> tilt_Space
tilt_Space: ExpressionEvaluator
    EXPRESSION = @Value(BLDGHEIGHT) / (@Value(SPACING)+0.00001)
    VAL_ATTR = _tiltSpace
    -> Chopper
Chopper
    MAX = 1
    CHOPPED -> CoordinateExtractor
CoordinateExtractor
    Z_ATTR = _z
    Y_ATTR = _y
    IND = 0
    Z_DEFAULT = -9999
    X_ATTR = _x
    -> tilt_y
tilt_y: ExpressionEvaluator
    EXPRESSION = @Value(_yBase) + ((@Value(_y) - @Value(_ymin)) / @Value(_tiltSpace)) * (1 - @Value(MARGIN))
    VAL_ATTR = _tiltY
    -> 2DPointReplacer
2DPointReplacer
    YVALATTR = @Value(_tiltY)
    XVALATTR = @Value(_x)
    POINT -> PointConnector
PointConnector
    BREAKATTR = FACROOM
    LINE -> GeometryCoercer_2
    POLYGON -> GeometryCoercer_2
GeometryCoercer_2
    KIND = fme_polygon
    CHECKZ = No
    COERCED -> SliverRemover_2
SliverRemover_2
    REPAIR_METHOD = Longest Boundary
    REPAIRED -> SelfIntersectChecker_4
SelfIntersectChecker_4
    NotSelfIntersecting -> OUTPUT (output)
OUTPUT (output)

FME custom transformer SelfIntersectChecker
Separates self-intersecting features from the rest of input. This custom transformer does not change the geometry of self-intersecting features. If you want to remove self-intersections, try the " SelfIntersector " transformer.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Input (input)
    -> PartCounter
PartCounter
    COUNT_ATTR = _part_count1
    RECURSIVE_PARAM = No
    -> COUNTER
COUNTER: Counter
    START = 0
    SCOPE = Local
    DOMAIN = counter
    CNT_ATTR = _selfID
    -> GeometryExtractor
GeometryExtractor
    ATTR = _geometry
    KIND_LONG = OGC Well Known Text
    OGCVERSION = 1.2
    -> SelfIntersector
SelfIntersector
    SEG_ATTR = _segments
    SELF_INTERSECTED -> DuplicateRemover
DuplicateRemover
    KEYATTR = _selfID
    UNIQUE -> TESTER
TESTER: Tester
    TEST_MODE = NUMERIC
    TEST_CLAUSE = TEST @Value(_segments) > 1
    BOOL_OP = OR
    TEST_LIST = &_segments,>,1
    PASSED -> GeometryReplacer
    FAILED -> PartCounter_2
PartCounter_2
    COUNT_ATTR = _part_count2
    RECURSIVE_PARAM = No
    -> TESTER_2
TESTER_2: Tester
    TEST_MODE = Automatic
    TEST_CLAUSE = TEST @Value(_part_count1) = @Value(_part_count2)
    BOOL_OP = OR
    TEST_LIST = &_part_count1,=,&_part_count2
    PASSED -> ATTRIBUTEREMOVER
    FAILED -> GeometryReplacer
ATTRIBUTEREMOVER: AttributeRemover
    REMOVE_ATTRS = _selfID,_geometry,_segments
    -> NotSelfIntersecting (output)
NotSelfIntersecting (output)
GeometryReplacer
    ATTR = _geometry
    KIND_LONG = OGC Well Known Text
    -> ATTRIBUTEREMOVER_2
ATTRIBUTEREMOVER_2: AttributeRemover
    REMOVE_ATTRS = _selfID,_geometry,_segments
    -> SelfIntersecting (output)
SelfIntersecting (output)

FME custom transformer gzBuildingOutline

Parameters:
- FACNUM = @Value(FACNUM)
- BUILDINGID = @Value(BUILDINGID)

INPUT (input)
    -> Chopper_2
    -> FeatureMerger_3 [input 1]
Chopper_2
    MAX = 2
    CHOPPED -> LengthCalculator_2
LengthCalculator_2
    MULT = 1
    DIM = 2
    LEN_ATTR = _length
    -> StatisticsCalculator_2
StatisticsCalculator_2
    MAX_ATTR = _max
    NUMERIC_ATTR = _numeric_count
    RANGE_ATTR = _range
    GROUP_BY = BUILDINGID
    SUM_ATTR = _sum
    MODE_ATTR = _mode
    COUNT_ATTR = _count
    PASS_THROUGH = Yes
    MEDIAN_ATTR = _median
    STATS_ATTR = _length
    MIN_ATTR = _min
    MEAN_ATTR = _mean
    STDEV_ATTR = _stdev
    STATISTICS -> TestFilter_6
TestFilter_6
    DEFAULT_VALUE = <UNFILTERED>
    TEST_LIST = BOOL_OP,OR,COMPOSITE_TEST,<Unused>,TEST_CLAUSE,"TEST ""@Value(_length)"" = ""@Value(_max)""",_length = _max
    _length = _max -> CoordinateExtractor_4
CoordinateExtractor_4
    Z_ATTR = _z
    Y_ATTR = _y1
    IND = 0
    Z_DEFAULT = -9999
    X_ATTR = _x1
    -> CoordinateExtractor_6
CoordinateExtractor_6
    Z_ATTR = _z
    Y_ATTR = _y2
    IND = 1
    Z_DEFAULT = -9999
    X_ATTR = _x2
    -> TestFilter_4
TestFilter_4
    DEFAULT_VALUE = <UNFILTERED>
    TEST_LIST = BOOL_OP,OR,COMPOSITE_TEST,<Unused>,TEST_CLAUSE,"TEST ""@Value(_y2)"" >= ""@Value(_y1)""",_y2 >= _y1
    _y2 >= _y1 -> ExpressionEvaluator_7
    <UNFILTERED> -> ExpressionEvaluator_4
Note: Calculate angle of the longest side
ExpressionEvaluator_7
    EXPRESSION = @atan2(@Value(_x1)-@Value(_x2),@Value(_y1)-@Value(_y2))*180.0/(22/7.0)
    VAL_ATTR = _angle
    -> ExpressionEvaluator_8
ExpressionEvaluator_4
    EXPRESSION = @atan2(@Value(_x2)-@Value(_x1),@Value(_y2)-@Value(_y1))*180.0/(22/7.0)
    VAL_ATTR = _angle
    -> ExpressionEvaluator_8
ExpressionEvaluator_8
    EXPRESSION = @Value(_angle) + 90.0
    VAL_ATTR = _angle
    -> TestFilter_5
TestFilter_5
    DEFAULT_VALUE = <UNFILTERED>
    TEST_LIST = BOOL_OP,OR,COMPOSITE_TEST,<Unused>,TEST_CLAUSE,"TEST ""@Value(_angle)"" > ""180.0""",_angle > 180.0
    _angle > 180.0 -> ExpressionEvaluator_10
    <UNFILTERED> -> Sorter_2
ExpressionEvaluator_10
    EXPRESSION = @Value(_angle) -180.0
    VAL_ATTR = _angle
    -> Sorter_2
Sorter_2
    SORT_PARM = _length NUMERIC DESCENDING
    SORTED -> FeatureMerger_3 [input 2]
FeatureMerger_3
    MERGE_TYPE = Attributes Only
    REFEEATTR = BUILDINGID
    BUILD_INCOMPLETE = No
    REFERATTR = BUILDINGID
    PROCESS_DUPS = No
    COMPLETE -> GeometryExtractor_2
GeometryExtractor_2
    ATTR = _geometry
    KIND_LONG = FME Binary
    -> CenterOfGravityReplacer
CenterOfGravityReplacer
    CENTEROFGRAVITY -> CoordinateExtractor_3
CoordinateExtractor_3
    Z_ATTR = _z
    Y_ATTR = YCENTER
    IND = 0
    Z_DEFAULT = -9999
    X_ATTR = XCENTER
    -> GeometryReplacer
GeometryReplacer
    ATTR = _geometry
    KIND_LONG = FME Binary
    -> AttributeCreator
Note: Calculate X and Y Center Point
AttributeCreator
    ATTR_LIST = BLDGHEIGHT,@Evaluate( abs(@Value(_y2) - @Value(_y1)) ),CALCROT,@Value(_angle)
    -> OUTPUT (output)
OUTPUT (output)

FME custom transformer gzAggregateLines
Clean geometries and Aggregate Floorplan lines into _Optimized features

INPUT (input)
    -> CoordinateCounter
CoordinateCounter
    CNT_ATTR = _coordcount
    -> LengthCalculator_2
LengthCalculator_2
    MULT = 1
    DIM = 2
    LEN_ATTR = _length
    -> TestFilter_6
TestFilter_6
    DEFAULT_VALUE = <UNFILTERED>
    TEST_LIST:
      BOOL_OP,AND,COMPOSITE_TEST,<Unused>,TEST_CLAUSE,"TEST ""@Value(_coordcount)"" >= ""2""
      TEST ""@Value(_length)"" >= "".001""",2pts & length > .01
    2pts & length > .01 -> SelfIntersectChecker
SelfIntersectChecker
    NotSelfIntersecting -> GeometryCoercer
    SelfIntersecting -> SelfIntersector
SelfIntersector
    SEG_ATTR = _segments
    SELF_INTERSECTED -> GeometryCoercer
GeometryCoercer
    KIND = fme_line
    COERCED -> Aggregator_2
Aggregator_2
    GROUP_BY = FACFLOOR
    ORDERED = No
    SEP = ,
    CONTAIN_INDIVID_GEOMS = No
    ACCUM_ATTRS_NAME = Yes
    AGGREGATE -> OUTPUT (output)
OUTPUT (output)
