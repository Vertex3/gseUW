FME workspace gseFloorplanArchive.fmw
Title: GizintaLoader
Description: First Beta release of Gizinta for FME
Usage: Add the xml file and other parameters
Requirements: test
History: 31/10/2013,support@Gizinta.com,First Draft
Legal terms conditions: This work is licensed under the Creative Commons Attribution-ShareAlike 3.0 Unported License.
Startup Python:
      import xml.dom.minidom
      import os
      import sys
      import time
      import fmeobjects

      ospath = FME_MacroValues['FME_MF_DIR']
      print ospath
      if ospath not in sys.path:
          sys.path.append(ospath)
      import gzfme

      ErrorUniqueID = "ErrorUniqueID"
      ErrorRequiredValue = "ErrorRequiredValue"
      ErrorValueMap = "ErrorValueMap"
      Errors = False

      debug = gzfme.setDebug(FME_MacroValues['gzDebug'])
      logger = fmeobjects.FMELogFile()
      gzfme.logger = logger
Shutdown Python:
      import fmeobjects, gzfme
      #gzfme.shutdown(Errors,str(FME_MacroValues['IgnoreErrors']),FME_TotalFeaturesWritten,FME_MacroValues)

      del Errors
      del ErrorUniqueID
      del ErrorRequiredValue
      del ErrorValueMap
      del debug
      del logger
      gzfme.logger = None

Parameters:
- DestDataset_GEODATABASE_SDE = sde   # Destination Esri ArcSDE Geodatabase Dataset
- OUT_CONNECTION_FILE_GEODATABASE_SDE = C:\Apps\Gizinta\gseUW\ETL\serverConfig\GIS Staging.sde   # Connection File
- ProductionConnectionFile = C:\Apps\Gizinta\gseUW\ETL\serverConfig\GIS Production.sde   # Enter the path and name of the Production SDE Database connection file
- GizintaProject = C:\Apps\Gizinta\gseUW\ETL\config\fpArchivePlaylist.xml   # Select the Gizinta Xml File to use
- SourceFieldQA = False   # Choose whether to perform QA on Source Fields
- TargetFieldQA = True   # Choose whether to perform QA on Target Fields
- IgnoreErrors = False   # Ignore Errors and continue
- SourceDatasetTypes = GDBDataset   # Enter the Gizinta Source Dataset Type
- pFLOORID = 1327_M3   # Enter the FLOORID
- gzDebug = True   # Enable gzDebug (True/False)
- LOG_FILE =   # Log File
- FEATURE_TYPES = FloorArea_All InteriorSpace_All InteriorSpace_Point_All FloorplanLine_All Floor_Point Floor_All FloorplanLine_Publish_All

Readers:
- GEODATABASE_SDE_1: GEODATABASE_SDE from $(DestDataset_GEODATABASE_SDE)
- GEODATABASE_SDE_2: GEODATABASE_SDE from $(DestDataset_GEODATABASE_SDE)

Writers:
- GEODATABASE_SDE_3: GEODATABASE_SDE to $(DestDataset_GEODATABASE_SDE)
- GEODATABASE_SDE_4: GEODATABASE_SDE to $(DestDataset_GEODATABASE_SDE)

Note: List controllled by Feature_Types parameter
DBO.InteriorSpace_Isometric_All (reader GEODATABASE_SDE_2)
    attributes: geodb_oid integer, OBJECTID integer, BUILDINGID char(4), FLOOR char(6), FLOORID char(12), ROOM char(26), SPACEID char(25), IN_DATE date, LAST_USER char(50), STACKLEVEL smallint, GlobalID char(38), SHAPE.STArea() double, SHAPE.STLength() double, HASFLOORPLANLINES char(3), ALTITUDE smallint, SOURCEID char(30), FACLEVEL char(14), HASINTERIORSPACES char(3), FACILITY_CODE char(254), SCALE_11X17 double, FLOOR_NAME char(254), SCALE_85X11 double, NAME_LONG char(255), FLOOR_LEVEL integer, SCHELEV smallint, CALCROT double, SOURCEDWG char(60), SPACE_AREA double, MODPORTRAIT double, HASFLOORAREAS char(3),
      LINETYPE char(24), FLOORAREA double, MODLANDSCAPE double, NAME char(254), NAME_SHORT char(255), WEBMERCROT double
    -> AttributeExposer
AttributeExposer
    ATTR_LIST = SPACEID,FLOORID,DRAWING,fme_feature_type
    -> Tester
Tester
    TEST_MODE = Automatic
    TEST_DESCRIPTION = ""
    BOOL_OP = OR
    TEST_CLAUSE = TEST @Value(FLOORID) = $(pFLOORID)
    PASSED -> gzWriteData
gzWriteData
    IgnoreErrors = False
    GroupBy = OBJECTID
    HASERRORS = @Value(DRAWING)
    gzLogWriter -> DBO.gzLog (writer GEODATABASE_SDE_3)
    gzErrorWriter -> DBO.gzError (writer GEODATABASE_SDE_3)
    gzFeatureWriter -> NewFeatureType (writer GEODATABASE_SDE_4)
DBO.gzLog (writer GEODATABASE_SDE_3)
    attributes: PROCNAME char(255), LOADTIME date, LOADNAME char(255), DATASET char(255), COMPLETED smallint, LOADUSER char(255), ACTIVEFLAG char(255)
Note: This is a delete writer to staging
NewFeatureType (writer GEODATABASE_SDE_4)
    attributes: FLOORID char(30)
DBO.gzError (writer GEODATABASE_SDE_3)
    attributes: PROCNAME char(255), SOURCENAME char(255), SRCIDFIELD char(255), SRCIDVAL char(255), DATASET char(255), REASON char(255), ERRUSER char(255), ERRTIME date, ACTIVEFLAG char(255)

FME custom transformer gzTiltRooms
Tilt Rooms in floorplans to create a pseudo-isometric view of the rooms and floors

Parameters:
- pBUILDINGID = 1327   # Enter the Building Identifier
- pFLOORID = 1327_01   # Enter the Floor ID
- ProductionConnectionFile = C:\Apps\Gizinta\gseUW\ETL\GIS Production.sde   # Enter the path and name of the Production SDE Connection

INPUT (input)
    -> DuplicateRemover
    -> FeatureMerger_2 [input 1]
    -> DuplicateRemover_2
DuplicateRemover_2
    KEYATTR = $(pBUILDINGID)
    UNIQUE -> BldgReader
BldgReader: FeatureReader
    GEODATABASE_SDE_RESOLVE_SUBTYPE_NAMES = yes
    GEODATABASE_SDE_SPLIT_COMPLEX_EDGES = no
    FEATURETYPES = DBO.FloorPageTemplate
    GEODATABASE_SDE_VERSION = SDE.DEFAULT
    GEODATABASE_SDE_TRANSLATE_SPATIAL_DATA_ONLY = no
    GEODATABASE_SDE_CONNECTION = Connection File
    COMBINE_GEOM = Keep result geometry only
    GEODATABASE_SDE_VERSION_TYPE = Connect using a Transactional Version
    COMBINE_ATTRS = Keep result attributes only
    GEODATABASE_SDE_REMOVE_TABLE_QUALIFIER = YES
    GEODATABASE_SDE_IGNORE_RELATIONSHIP_INFO = yes
    GEODATABASE_SDE_WHERE = BUILDINGID=$(pBUILDINGID)
    SUPPORTED_SPATIAL_INTERACTIONS = ENVELOPE_INTERSECT%INTERSECTS%CONTAINS%CROSSES%DISJOINT%EQUALS%OVERLAPS%TOUCHES%WITHIN
    DATASET = sde
    GEODATABASE_SDE_TABLELIST = DBO.FloorPageTemplate
    GEODATABASE_SDE_SPLIT_MULTI_PART_ANNOS = no
    ATTRIBUTES = DBO.FloorPageTemplate,"geodb_oid,OBJECTID,BUILDINGID,HULLROT,BLDGHEIGHT,SPACING,MARGIN,XCENTER,YCENTER,SOURCEID,SOURCEDWG,IN_DATE,LAST_USER,GlobalID,SHAPE.STArea(),SHAPE.STLength()"
    GEODATABASE_SDE_RESOLVE_DOMAINS = no
    FORMAT = GEODATABASE_SDE
    GEODATABASE_SDE_CONNECTION_FILE = $(ProductionConnectionFile)
    GEODATABASE_SDE_IGNORE_NETWORK_INFO = yes
    DBO.FloorPageTemplate -> BoundsExtractor_2
BoundsExtractor_2
    YMIN = _ymin
    ZMIN = _zmin
    XMIN = _xmin
    XMAX = _xmax
    ZMAX = _zmax
    YMAX = _ymax
    -> FeatureMerger_2 [input 2]
FeatureMerger_2
    PROCESS_DUPS = No
    MERGE_TYPE = Attributes Only
    SUPPLIERS_FIRST = No
    JOIN_KEYS = @Value(BUILDINGID) $(pBUILDINGID)
    SUPPLIER_PREFIX_DUMMY = YES
    MERGED -> FeatureMerger_3 [input 1]
DuplicateRemover
    KEYATTR = $(pBUILDINGID)
    UNIQUE -> FloorsReader
FloorsReader: FeatureReader
    GEODATABASE_SDE_RESOLVE_SUBTYPE_NAMES = yes
    GEODATABASE_SDE_SPLIT_COMPLEX_EDGES = no
    FEATURETYPES = DBO.Active_Floor
    GEODATABASE_SDE_VERSION = SDE.DEFAULT
    GEODATABASE_SDE_TRANSLATE_SPATIAL_DATA_ONLY = no
    GEODATABASE_SDE_CONNECTION = Connection File
    COMBINE_GEOM = In case of conflict, keep aggregate of INITIATOR and result geometry
    GEODATABASE_SDE_VERSION_TYPE = Connect using a Transactional Version
    COMBINE_ATTRS = In case of conflict, keep result attributes
    GEODATABASE_SDE_REMOVE_TABLE_QUALIFIER = NO
    GEODATABASE_SDE_IGNORE_RELATIONSHIP_INFO = yes
    GEODATABASE_SDE_WHERE = BUILDINGID=$(pBUILDINGID)
    SUPPORTED_SPATIAL_INTERACTIONS = ENVELOPE_INTERSECT%INTERSECTS%CONTAINS%CROSSES%DISJOINT%EQUALS%OVERLAPS%TOUCHES%WITHIN
    DATASET = sde
    GEODATABASE_SDE_TABLELIST = DBO.Active_Floor
    GEODATABASE_SDE_SPLIT_MULTI_PART_ANNOS = no
    ATTRIBUTES = DBO.Active_Floor,"geodb_oid,OBJECTID,BUILDINGID,FLOOR,FLOORID,DWG_NAME,INTERIORSPACE,FLOORPLANLINE,SCHELEV,ALTITUDE,GlobalID"
    GEODATABASE_SDE_RESOLVE_DOMAINS = no
    FORMAT = GEODATABASE_SDE
    GEODATABASE_SDE_CONNECTION_FILE = $(ProductionConnectionFile)
    GEODATABASE_SDE_IGNORE_NETWORK_INFO = yes
    DBO.Active_Floor -> AttributeCopier_3
AttributeCopier_3
    ATTR_LIST = STACKLEVEL,SCHELEV
    -> FeatureMerger_3 [input 2]
FeatureMerger_3
    PROCESS_DUPS = No
    MERGE_TYPE = Attributes Only
    SUPPLIERS_FIRST = No
    JOIN_KEYS = @Value(FLOORID) $(pFLOORID)
    SUPPLIER_PREFIX_DUMMY = YES
    MERGED -> ExpressionEvaluator_2
ExpressionEvaluator_2
    VAL_ATTR = CALCULATED_ROTATION
    EXPRESSION = @Value(HULLROT) + 15.0
    -> Rotator
Rotator
    YORIG = @Value(_ymin)
    ANGLE = @Value(CALCULATED_ROTATION)
    XORIG = @Value(_xmin)
    ROTATED -> Y_Base
Y_Base: ExpressionEvaluator
    VAL_ATTR = _yBase
    EXPRESSION = @Value(_ymin) + (@Value(SPACING) * @Value(STACKLEVEL))
    -> tilt_Space
tilt_Space: ExpressionEvaluator
    VAL_ATTR = _tiltSpace
    EXPRESSION = @Value(BLDGHEIGHT) / (@Value(SPACING)+0.00001)
    -> Chopper
Chopper
    MAX = 1
    CHOPPED -> CoordinateExtractor
CoordinateExtractor
    Y_ATTR = _y
    X_ATTR = _x
    Z_DEFAULT = -9999
    Z_ATTR = _z
    IND = 0
    -> tilt_y
tilt_y: ExpressionEvaluator
    VAL_ATTR = _tiltY
    EXPRESSION = @Value(_yBase) + ((@Value(_y) - @Value(_ymin)) / @Value(_tiltSpace)) * (1 - @Value(MARGIN))
    -> 2DPointReplacer
2DPointReplacer
    XVALATTR = @Value(_x)
    YVALATTR = @Value(_tiltY)
    POINT -> PointConnector
PointConnector
    BREAKATTR = SPACEID
    POLYGON -> GeometryCoercer_2
    LINE -> GeometryCoercer_2
GeometryCoercer_2
    CHECKZ = No
    KIND = fme_polygon
    COERCED -> SelfIntersectChecker_2
SelfIntersectChecker_2
    NotSelfIntersecting -> OUTPUT (output)
    SelfIntersecting -> Logger_SelfIntersecting
OUTPUT (output)
Logger_SelfIntersecting
    MESSAGE = Feature is:
    MAXFEATS = 20
    MAXCOORDS = 20

FME custom transformer gzSetupExtract

INPUT (input)
    -> AttributeExposer
AttributeExposer
    ATTR_LIST = fme_feature_type_name
    -> PythonCaller
PythonCaller
    PYTHONSOURCE:
      import fmeobjects


      # Template Function interface:
      def processFeature(feature):
          pass

      # Template Class Interface:
      class FeatureProcessor(object):
          def __init__(self):
              pass
          def input(self,feature):
              whereClause = ""
              featType = feature.getAttribute("fme_feature_type_name")
              for sourceDataset in sourceDatasets:
                  sourceName = sourceDataset.getAttributeNode("sourceName").nodeValue
                  if debug == True:
                      logger.logMessageString("gz sources=" + featType + "|" + sourceName)
                  if sourceName == featType:
                      whereClause = getWhereClause(featType)
                      if debug == True:
                          logger.logMessageString("gz Where=" + whereClause)
                      feature.setAttribute("WhereClause",whereClause)
                      self.pyoutput(feature)

          def close(self):
              pass
    PYTHONSYMBOL = FeatureProcessor
    NEW_ATTRIBUTES = WhereClause *
    -> OUTPUT (output)
OUTPUT (output)

FME custom transformer gzBuildingAngle

Parameters:
- BUILDINGID =   # Enter the Building ID

INPUT (input)
    -> Chopper_2
    -> FeatureMerger_3 [input 1]
Chopper_2
    MAX = 2
    CHOPPED -> LengthCalculator_2
LengthCalculator_2
    LEN_ATTR = _length
    MULT = 1
    DIM = 2
    -> StatisticsCalculator_2
StatisticsCalculator_2
    STATS_ATTR = _length
    PASS_THROUGH = Yes
    MAX_ATTR = _max
    RANGE_ATTR = _range
    SUM_ATTR = _sum
    COUNT_ATTR = _count
    NUMERIC_ATTR = _numeric_count
    STDEV_ATTR = _stdev
    MODE_ATTR = _mode
    MEDIAN_ATTR = _median
    MIN_ATTR = _min
    MEAN_ATTR = _mean
    STATISTICS -> TestFilter_6
TestFilter_6
    TEST_LIST = BOOL_OP,OR,COMPOSITE_TEST,<Unused>,TEST_CLAUSE,"TEST ""@Value(_length)"" = ""@Value(_max)""",_length = _max
    DEFAULT_VALUE = <UNFILTERED>
    _length = _max -> CoordinateExtractor_4
CoordinateExtractor_4
    Y_ATTR = _y1
    X_ATTR = _x1
    Z_DEFAULT = -9999
    Z_ATTR = _z
    IND = 0
    -> CoordinateExtractor_6
CoordinateExtractor_6
    Y_ATTR = _y2
    X_ATTR = _x2
    Z_DEFAULT = -9999
    Z_ATTR = _z
    IND = 1
    -> TestFilter_4
TestFilter_4
    TEST_LIST = BOOL_OP,OR,COMPOSITE_TEST,<Unused>,TEST_CLAUSE,"TEST ""@Value(_y2)"" >= ""@Value(_y1)""",_y2 >= _y1
    DEFAULT_VALUE = <UNFILTERED>
    _y2 >= _y1 -> ExpressionEvaluator_7
    <UNFILTERED> -> ExpressionEvaluator_4
Note: Calculate angle of the longest side
ExpressionEvaluator_7
    VAL_ATTR = _angle
    EXPRESSION = @atan2(@Value(_x1)-@Value(_x2),@Value(_y1)-@Value(_y2))*180.0/(22/7.0)
    -> ExpressionEvaluator_8
ExpressionEvaluator_4
    VAL_ATTR = _angle
    EXPRESSION = @atan2(@Value(_x2)-@Value(_x1),@Value(_y2)-@Value(_y1))*180.0/(22/7.0)
    -> ExpressionEvaluator_8
ExpressionEvaluator_8
    VAL_ATTR = _angle
    EXPRESSION = @Value(_angle) + 90.0
    -> TestFilter_5
TestFilter_5
    TEST_LIST = BOOL_OP,OR,COMPOSITE_TEST,<Unused>,TEST_CLAUSE,"TEST ""@Value(_angle)"" > ""180.0""",_angle > 180.0
    DEFAULT_VALUE = <UNFILTERED>
    _angle > 180.0 -> ExpressionEvaluator_10
    <UNFILTERED> -> Sorter_2
ExpressionEvaluator_10
    VAL_ATTR = _angle
    EXPRESSION = @Value(_angle) -180.0
    -> Sorter_2
Sorter_2
    SORT_PARM = _length NUMERIC DESCENDING
    SORTED -> FeatureMerger_3 [input 2]
FeatureMerger_3
    BUILD_INCOMPLETE = No
    PROCESS_DUPS = No
    MERGE_TYPE = Attributes Only
    REFERATTR = $(BUILDINGID)
    REFEEATTR = $(BUILDINGID)
    COMPLETE -> GeometryExtractor_2
GeometryExtractor_2
    ATTR = _geometry
    KIND_LONG = FME Binary
    -> CenterOfGravityReplacer
CenterOfGravityReplacer
    CENTEROFGRAVITY -> CoordinateExtractor_3
CoordinateExtractor_3
    Y_ATTR = YCENTER
    X_ATTR = XCENTER
    Z_DEFAULT = -9999
    Z_ATTR = _z
    IND = 0
    -> GeometryReplacer
GeometryReplacer
    ATTR = _geometry
    KIND_LONG = FME Binary
    -> AttributeCreator
Note: Calculate X and Y Center Point
AttributeCreator
    ATTR_LIST = MODANGLE,0,SPACING,50,MARGIN,.2,HULLROT,@Value(_angle)
    -> OUTPUT (output)
OUTPUT (output)

FME custom transformer gzFixIntersections

Parameters:
- Tolerance = 0.001   # Generalization tolerance
- UniqueIDName = SPACEID   # UniqueID field name for polygons
- Feature_Type = InteriorSpace_All   # Feature Type to process

INPUT (input)
    -> AttributeExposer
AttributeExposer
    ATTR_LIST = fme_feature_type,DRAWING,BUILDINGID,FLOORID
    -> Tester
Tester
    TEST_MODE = Automatic
    TEST_DESCRIPTION = ""
    BOOL_OP = OR
    TEST_CLAUSE = TEST @Value(fme_feature_type) = $(Feature_Type)
    PASSED -> Generalizer
Generalizer
    ALG_TEXT = Douglas (Generalize)
    PRESERVE = No
    TOLERANCE = $(Tolerance)
    -> GeometryValidator
GeometryValidator
    CHECK_HOLE_TOUCHING_POLYGON = No
    DUP_COORDS_CHECK_Z = Yes
    NULL_REMOVAL = NULL_REMOVAL
    SELF_INTERSECTING = SELF_INTERSECTING
    PRESETS = Custom
    ARC_ENDPOINT_TOLERANCE_MODE = Auto
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%""%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    REPAIR = Yes
    ISSUE_ATTR_NAME = _issues
    PLANAR_TOLERANCE_MODE = Auto
    NAN_REMOVAL = NAN_REMOVAL
    CONSECUTIVE_IDENTICAL_VERTICES_2D = CONSECUTIVE_IDENTICAL_VERTICES_2D
    PASSED -> GeometryCoercer_2
    REPAIRED -> GeometryCoercer_2
GeometryCoercer_2
    CHECKZ = No
    KIND = fme_polygon
    COERCED -> SelfIntersectChecker_2
SelfIntersectChecker_2
    SelfIntersecting -> Logger_SelfIntersecting
    NotSelfIntersecting -> OUTPUT (output)
OUTPUT (output)
Logger_SelfIntersecting
    MESSAGE = Feature is self-intersecting:
    MAXFEATS = 100
    MAXCOORDS = 20

FME custom transformer gseFloorPoint

Parameters:
- ProductionConnectionFile = C:\Apps\Gizinta\gseUW\ETL\GIS Production.sde   # Enter the path and name of the Production SDE Connection

INPUT (input)
    -> TestFilter
TestFilter
    TEST_LIST:
      BOOL_OP,OR,COMPOSITE_TEST,<Unused>,TEST_CLAUSE,"TEST @Value(fme_feature_type) = FloorplanLine_All
      TEST @Value(fme_feature_type) = DBO.FloorplanLine_All",FloorplanLine_All,BOOL_OP,OR,COMPOSITE_TEST,<Unused>,TEST_CLAUSE,"TEST @Value(fme_feature_type) = InteriorSpace_All
      TEST @Value(fme_feature_type) = DBO.InteriorSpace_All",InteriorSpace_All,BOOL_OP,OR,COMPOSITE_TEST,<Unused>,TEST_CLAUSE,"TEST @Value(fme_feature_type) = Floor_All
      TEST @Value(fme_feature_type) = DBO.Floor_All",Floor_All
    DEFAULT_VALUE = <UNFILTERED>
    FloorplanLine_All -> StatisticsCalculator
    InteriorSpace_All -> StatisticsCalculator_2
    Floor_All -> StatisticsCalculator_3
    Floor_All -> FeatureMerger_3 [input 1]
    Floor_All -> FeatureReader_3
    Floor_All -> FeatureReader_4
    Floor_All -> FeatureReader_2
StatisticsCalculator
    COMPUTE_HISTOGRAM = NO
    STATS_ATTRS = OBJECTID FLOORID
    COUNT_ATTR = _count
    NUMERIC_ATTR = _numeric_count
    MIN_ATTR = _value
    PREPEND_ATTR_NAME_CHOICE = Automatically
    SUMMARY -> AttributeCreator_2
AttributeCreator_2
    ATTR_LIST = HASFLOORPLANLINES,@Value(FLOORID._count)
    -> FeatureMerger_6 [input 1]
StatisticsCalculator_2
    COMPUTE_HISTOGRAM = NO
    STATS_ATTRS = OBJECTID FLOORID
    COUNT_ATTR = _count
    NUMERIC_ATTR = _numeric_count
    MIN_ATTR = _value
    PREPEND_ATTR_NAME_CHOICE = Automatically
    SUMMARY -> AttributeCreator_3
AttributeCreator_3
    ATTR_LIST = HASINTERIORSPACES,@Value(FLOORID._count)
    -> FeatureMerger_6 [input 2]
FeatureMerger_6
    PROCESS_DUPS = No
    MERGE_TYPE = Attributes Only
    SUPPLIERS_FIRST = No
    JOIN_KEYS = @Value(FLOORID._value) @Value(FLOORID._value)
    SUPPLIER_PREFIX_DUMMY = YES
    MERGED -> FeatureMerger_5 [input 1]
    NOT_MERGED -> FeatureMerger_5 [input 1]
StatisticsCalculator_3
    COMPUTE_HISTOGRAM = NO
    STATS_ATTRS = OBJECTID FLOORID
    COUNT_ATTR = _count
    NUMERIC_ATTR = _numeric_count
    MIN_ATTR = _value
    PREPEND_ATTR_NAME_CHOICE = Automatically
    SUMMARY -> AttributeCreator_4
AttributeCreator_4
    ATTR_LIST = HASFLOORAREAS,@Value(FLOORID._count)
    -> FeatureMerger_5 [input 2]
FeatureMerger_5
    PROCESS_DUPS = No
    MERGE_TYPE = Attributes Only
    SUPPLIERS_FIRST = No
    JOIN_KEYS = @Value(FLOORID._value) @Value(FLOORID._value)
    SUPPLIER_PREFIX_DUMMY = YES
    MERGED -> FeatureMerger_4 [input 2]
    NOT_MERGED -> FeatureMerger_4 [input 2]
FeatureReader_3
    GEODATABASE_SDE_RESOLVE_SUBTYPE_NAMES = yes
    GEODATABASE_SDE_SPLIT_COMPLEX_EDGES = no
    FEATURETYPES = DBO.Building_Point DBO.Active_Floor
    GEODATABASE_SDE_VERSION = SDE.DEFAULT
    GEODATABASE_SDE_TRANSLATE_SPATIAL_DATA_ONLY = no
    GEODATABASE_SDE_CONNECTION = Connection File
    COMBINE_GEOM = Keep result geometry only
    GEODATABASE_SDE_VERSION_TYPE = Connect using a Transactional Version
    COMBINE_ATTRS = In case of conflict, keep result attributes
    GEODATABASE_SDE_REMOVE_TABLE_QUALIFIER = YES
    GEODATABASE_SDE_IGNORE_RELATIONSHIP_INFO = yes
    SUPPORTED_SPATIAL_INTERACTIONS = ENVELOPE_INTERSECT%INTERSECTS%CONTAINS%CROSSES%DISJOINT%EQUALS%OVERLAPS%TOUCHES%WITHIN
    DATASET = sde
    GEODATABASE_SDE_TABLELIST = DBO.Building_Point DBO.Active_Floor
    GEODATABASE_SDE_SPLIT_MULTI_PART_ANNOS = no
    ATTRIBUTES = DBO.Building_Point,,DBO.Active_Floor,
    GEODATABASE_SDE_RESOLVE_DOMAINS = no
    FORMAT = GEODATABASE_SDE
    GEODATABASE_SDE_CONNECTION_FILE = $(ProductionConnectionFile)
    GEODATABASE_SDE_IGNORE_NETWORK_INFO = yes
    DBO.Building_Point -> FeatureMerger_3 [input 2]
    DBO.Active_Floor -> FeatureMerger [input 2]
FeatureMerger_3
    GROUP_BY = BUILDINGID
    PROCESS_DUPS = No
    MERGE_TYPE = Attributes and Geometry
    SUPPLIERS_FIRST = No
    JOIN_KEYS = @Value(BUILDINGID) @Value(BUILDINGID)
    SUPPLIER_PREFIX_DUMMY = YES
    MERGED -> FeatureMerger [input 1]
    NOT_MERGED -> FeatureMerger [input 1]
FeatureMerger
    GROUP_BY = BUILDINGID
    PROCESS_DUPS = No
    MERGE_TYPE = Attributes Only
    SUPPLIERS_FIRST = No
    JOIN_KEYS = @Value(BUILDINGID) @Value(BUILDINGID)
    SUPPLIER_PREFIX_DUMMY = YES
    MERGED -> FeatureMerger_7 [input 1]
    NOT_MERGED -> FeatureMerger_7 [input 1]
FeatureReader_4
    GEODATABASE_SDE_RESOLVE_SUBTYPE_NAMES = yes
    GEODATABASE_SDE_SPLIT_COMPLEX_EDGES = no
    FEATURETYPES = DBO.FloorPageTemplate
    GEODATABASE_SDE_VERSION = SDE.DEFAULT
    GEODATABASE_SDE_TRANSLATE_SPATIAL_DATA_ONLY = no
    GEODATABASE_SDE_CONNECTION = Connection File
    COMBINE_GEOM = Keep result geometry only
    GEODATABASE_SDE_VERSION_TYPE = Connect using a Transactional Version
    COMBINE_ATTRS = In case of conflict, keep result attributes
    GEODATABASE_SDE_REMOVE_TABLE_QUALIFIER = NO
    GEODATABASE_SDE_IGNORE_RELATIONSHIP_INFO = yes
    SUPPORTED_SPATIAL_INTERACTIONS = ENVELOPE_INTERSECT%INTERSECTS%CONTAINS%CROSSES%DISJOINT%EQUALS%OVERLAPS%TOUCHES%WITHIN
    DATASET = sde
    GEODATABASE_SDE_TABLELIST = DBO.FloorPageTemplate
    GEODATABASE_SDE_SPLIT_MULTI_PART_ANNOS = no
    ATTRIBUTES = DBO.FloorPageTemplate,"geodb_oid,OBJECTID,BUILDINGID,HULLROT,BLDGHEIGHT,SPACING,MARGIN,XCENTER,YCENTER,CALCROT,WORLDFILE,SOURCEID,SOURCEDWG,IN_DATE,LAST_USER,GlobalID,SHAPE.STArea(),SHAPE.STLength()"
    GEODATABASE_SDE_RESOLVE_DOMAINS = no
    FORMAT = GEODATABASE_SDE
    GEODATABASE_SDE_CONNECTION_FILE = $(ProductionConnectionFile)
    GEODATABASE_SDE_IGNORE_NETWORK_INFO = yes
    DBO.FloorPageTemplate -> FeatureMerger_7 [input 2]
FeatureMerger_7
    GROUP_BY = BUILDINGID
    PROCESS_DUPS = No
    MERGE_TYPE = Attributes Only
    SUPPLIER_PREFIX = _tilt
    SUPPLIERS_FIRST = No
    JOIN_KEYS = @Value(FLOORID) @Value(FLOORID)
    SUPPLIER_PREFIX_DUMMY = YES
    MERGED -> FeatureMerger_2 [input 1]
    NOT_MERGED -> FeatureMerger_2 [input 1]
FeatureReader_2
    GEODATABASE_SDE_RESOLVE_SUBTYPE_NAMES = yes
    GEODATABASE_SDE_SPLIT_COMPLEX_EDGES = no
    FEATURETYPES = DBO.Floor_Level
    GEODATABASE_SDE_VERSION = SDE.DEFAULT
    GEODATABASE_SDE_TRANSLATE_SPATIAL_DATA_ONLY = no
    GEODATABASE_SDE_CONNECTION = Connection File
    COMBINE_GEOM = Keep result geometry only
    GEODATABASE_SDE_VERSION_TYPE = Connect using a Transactional Version
    COMBINE_ATTRS = In case of conflict, keep result attributes
    GEODATABASE_SDE_REMOVE_TABLE_QUALIFIER = NO
    GEODATABASE_SDE_IGNORE_RELATIONSHIP_INFO = yes
    SUPPORTED_SPATIAL_INTERACTIONS = ENVELOPE_INTERSECT%INTERSECTS%CONTAINS%CROSSES%DISJOINT%EQUALS%OVERLAPS%TOUCHES%WITHIN
    DATASET = sde
    GEODATABASE_SDE_TABLELIST = DBO.Floor_Level
    GEODATABASE_SDE_SPLIT_MULTI_PART_ANNOS = no
    ATTRIBUTES = DBO.Floor_Level,"geodb_oid,OBJECTID,FLOOR,FLOOR_LEVEL,NAME_LONG,NAME_SHORT,GlobalID"
    GEODATABASE_SDE_RESOLVE_DOMAINS = no
    FORMAT = GEODATABASE_SDE
    GEODATABASE_SDE_CONNECTION_FILE = $(ProductionConnectionFile)
    GEODATABASE_SDE_IGNORE_NETWORK_INFO = yes
    DBO.Floor_Level -> FeatureMerger_2 [input 2]
FeatureMerger_2
    PROCESS_DUPS = No
    MERGE_TYPE = Attributes Only
    SUPPLIER_PREFIX = _floorlevel
    SUPPLIERS_FIRST = No
    JOIN_KEYS = @Value(FLOOR) @Value(FLOOR)
    SUPPLIER_PREFIX_DUMMY = YES
    MERGED -> FeatureMerger_4 [input 1]
    NOT_MERGED -> FeatureMerger_4 [input 1]
FeatureMerger_4
    PROCESS_DUPS = No
    MERGE_TYPE = Attributes Only
    SUPPLIERS_FIRST = No
    JOIN_KEYS = @Value(FLOORID) @Value(FLOORID._value)
    SUPPLIER_PREFIX_DUMMY = YES
    MERGED -> AttributeCreator
AttributeCreator
    ATTR_LIST = fme_feature_type,Floor_Point,CALCROT,@Value(_tiltCALCROT),WORLDFILE,@Value(_tiltWORLDFILE),SCHELEV,@Value(_floorlevelSCHELEV),ALTITUDE,@Value(_floorlevelALTITUDE),FLOOR_LEVEL,@Value(_floorlevelFLOOR_LEVEL)
    -> OUTPUT (output)
OUTPUT (output)

FME custom transformer SelfIntersectChecker
Separates self-intersecting features from the rest of input. This custom transformer does not change the geometry of self-intersecting features. If you want to remove self-intersections, try the " SelfIntersector " transformer.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Input (input)
    -> PartCounter
PartCounter
    COUNT_ATTR = _part_count1
    RECURSIVE_PARAM = No
    -> COUNTER
COUNTER: Counter
    SCOPE = Local
    START = 0
    DOMAIN = counter
    CNT_ATTR = _selfID
    -> GeometryExtractor
GeometryExtractor
    OGCVERSION = 1.2
    ATTR = _geometry
    KIND_LONG = OGC Well Known Text
    -> SelfIntersector
SelfIntersector
    SEG_ATTR = _segments
    SELF_INTERSECTED -> DuplicateRemover
DuplicateRemover
    KEYATTR = _selfID
    UNIQUE -> TESTER
TESTER: Tester
    TEST_MODE = NUMERIC
    BOOL_OP = OR
    TEST_LIST = &_segments,>,1
    TEST_CLAUSE = TEST @Value(_segments) > 1
    FAILED -> PartCounter_2
    PASSED -> GeometryReplacer
PartCounter_2
    COUNT_ATTR = _part_count2
    RECURSIVE_PARAM = No
    -> TESTER_2
TESTER_2: Tester
    TEST_MODE = Automatic
    BOOL_OP = OR
    TEST_LIST = &_part_count1,=,&_part_count2
    TEST_CLAUSE = TEST @Value(_part_count1) = @Value(_part_count2)
    PASSED -> ATTRIBUTEREMOVER
    FAILED -> GeometryReplacer
ATTRIBUTEREMOVER: AttributeRemover
    REMOVE_ATTRS = _selfID,_geometry,_segments
    -> NotSelfIntersecting (output)
NotSelfIntersecting (output)
GeometryReplacer
    ATTR = _geometry
    KIND_LONG = OGC Well Known Text
    -> ATTRIBUTEREMOVER_2
ATTRIBUTEREMOVER_2: AttributeRemover
    REMOVE_ATTRS = _selfID,_geometry,_segments
    -> SelfIntersecting (output)
SelfIntersecting (output)

FME custom transformer gzAggregateLines
Clean geometries and Aggregate Floorplan lines into _Optimized features

INPUT (input)
    -> CoordinateCounter
CoordinateCounter
    CNT_ATTR = _coordcount
    -> LengthCalculator_2
LengthCalculator_2
    LEN_ATTR = _length
    MULT = 1
    DIM = 2
    -> TestFilter_6
TestFilter_6
    TEST_LIST:
      BOOL_OP,AND,COMPOSITE_TEST,<Unused>,TEST_CLAUSE,"TEST ""@Value(_coordcount)"" >= ""2""
      TEST ""@Value(_length)"" >= "".001""",2pts & length > .01
    DEFAULT_VALUE = <UNFILTERED>
    2pts & length > .01 -> GeometryCoercer_2
GeometryCoercer_2
    KIND = fme_line
    COERCED -> GeometryFilter
GeometryFilter
    BREAK_AGG = No
    LINE -> SelfIntersector
    ARC -> SelfIntersector
SelfIntersector
    SEG_ATTR = _segments
    SELF_INTERSECTED -> GeometryCoercer
GeometryCoercer
    KIND = fme_line
    COERCED -> LengthCalculator
LengthCalculator
    LEN_ATTR = _length
    MULT = 1
    DIM = 2
    -> Tester
Tester
    TEST_MODE = Automatic
    TEST_DESCRIPTION = ""
    BOOL_OP = OR
    TEST_CLAUSE = TEST @Value(_length) > .1
    PASSED -> GeometryFilter_2
GeometryFilter_2
    BREAK_AGG = No
    ARC -> SelfIntersector_2
    LINE -> SelfIntersector_2
SelfIntersector_2
    SEG_ATTR = _segments
    SELF_INTERSECTED -> GeometryCoercer_3
GeometryCoercer_3
    KIND = fme_line
    COERCED -> LengthCalculator_3
LengthCalculator_3
    LEN_ATTR = _length
    MULT = 1
    DIM = 2
    -> Tester_2
Tester_2
    TEST_MODE = Automatic
    TEST_DESCRIPTION = ""
    BOOL_OP = OR
    TEST_CLAUSE = TEST @Value(_length) > .1
    PASSED -> Aggregator_2
Aggregator_2
    GROUP_BY = FLOORID
    SEP = ,
    CONTAIN_INDIVID_GEOMS = No
    ACCUM_ATTRS_NAME = Yes
    ORDERED = No
    AGGREGATE -> OUTPUT (output)
OUTPUT (output)
