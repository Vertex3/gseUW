FME workspace gseFloorplanDerive.fmw
Title: GizintaLoader
Description: First Beta release of Gizinta for FME
Usage: Add the xml file and other parameters
Requirements: test
History: 31/10/2013,support@Gizinta.com,First Draft
Legal terms conditions: This work is licensed under the Creative Commons Attribution-ShareAlike 3.0 Unported License.
Startup Python:
      import xml.dom.minidom
      import os
      import sys
      import time
      import fmeobjects

      ospath = FME_MacroValues['FME_MF_DIR']
      print ospath
      if ospath not in sys.path:
          sys.path.append(ospath)
      import gzfme

      ErrorUniqueID = "ErrorUniqueID"
      ErrorRequiredValue = "ErrorRequiredValue"
      ErrorValueMap = "ErrorValueMap"
      Errors = False

      debug = gzfme.setDebug(FME_MacroValues['gzDebug'])
      logger = fmeobjects.FMELogFile()
      gzfme.logger = logger
Shutdown Python:
      import fmeobjects, gzfme

      gzfme.shutdown(Errors,str(FME_MacroValues['IgnoreErrors']),FME_TotalFeaturesWritten,FME_MacroValues)

      del Errors
      del ErrorUniqueID
      del ErrorRequiredValue
      del ErrorValueMap
      del debug
      del logger
      gzfme.logger = None

Parameters:
- DestDataset_GEODATABASE_SDE = sde   # Destination Esri ArcSDE Geodatabase Dataset
- OUT_CONNECTION_FILE_GEODATABASE_SDE = C:\Apps\Gizinta\gseUW\ETL\serverConfig\GIS Staging.sde   # Connection File
- ProductionConnectionFile = C:\Apps\Gizinta\gseUW\ETL\serverConfig\GIS Production.sde   # Enter the path and name of the Production SDE Database connection file
- GizintaProject = C:\Apps\Gizinta\gseUW\ETL\config\fpDerivePlaylist.xml   # Select the Gizinta Xml File to use
- SourceFieldQA = False   # Choose whether to perform QA on Source Fields
- TargetFieldQA = True   # Choose whether to perform QA on Target Fields
- IgnoreErrors = False   # Ignore Errors and continue
- SourceDatasetTypes = GDBDataset   # Enter the Gizinta Source Dataset Type
- flr = 1100%   # Enter the FloorID or like expression
- gzDebug = False   # Enable gzDebug (True/False)
- LOG_FILE = gseFloorplanDerive.log   # Log File
- FEATURE_TYPES = InteriorSpace_Tilt FloorplanLine InteriorSpace Floor_Outline Floor_Point Floor_Poly FloorplanLine_Publish FloorArea InteriorSpace_Point   # Feature Types to Write
- FEATURE_TYPES_READ = Floor_Poly InteriorSpace FloorplanLine
- truncate = Y   # Truncate before load option
- FEATURE_TYPES_PROD = AllFloors FloorPageTemplate
- elevName = schelev   # Floor Elevation Value Name

Readers:
- GEODATABASE_SDE_1: GEODATABASE_SDE from $(DestDataset_GEODATABASE_SDE)
- GEODATABASE_SDE_2: GEODATABASE_SDE from $(DestDataset_GEODATABASE_SDE)
- GEODATABASE_SDE_3: GEODATABASE_SDE

Writers:
- GEODATABASE_SDE_4: GEODATABASE_SDE to $(DestDataset_GEODATABASE_SDE)

DBO.FloorArea (reader GEODATABASE_SDE_2)
    attributes: geodb_oid integer, OBJECTID integer, SITEID char(60), BUILDINGID char(60), FLOOR char(20), FLOORID char(60), FLOORAREA double, SCHELEV smallint, ALTITUDE smallint, SENSITIVITY char(20), SOURCEDWG char(60), IN_DATE date, LAST_USER char(30), GlobalID char(38), FLOOR_NAME char(60), BLDG_NAME char(60), SHAPE.STArea() double, SHAPE.STLength() double
    -> AttributeExposer_2
AttributeExposer_2
    ATTR_LIST = fme_feature_type,SPACEID,FLOORID,FLOORAREA
    -> TestFeatureTypes
TestFeatureTypes: Tester
    TEST_MODE = Automatic
    TEST_DESCRIPTION = ""
    BOOL_OP = OR
    TEST_CLAUSE = TEST $(FEATURE_TYPES_READ) CONTAINS @Value(fme_feature_type)
    PASSED -> BulkAttributeRenamer_2
BulkAttributeRenamer_2
    CASE_CHANGE_TYPE = lowercase
    ATTRCHOICE = All Attributes
    PATTERN_ACTION_DISP = Change Case
    -> FeatureMerger [input 1]
FloorPageTemplate (reader GEODATABASE_SDE_3)
    attributes: OBJECTID integer, SITEID char(60), BUILDINGID char(60), CALCROT double, LOCALROT double, SOURCEID char(30), SOURCEDWG char(60), LASTUPDATE date, LASTEDITOR char(30), SHAPE.STArea() double, SHAPE.STLength() double, SCHELEV integer, FLOORLEVEL integer, GROUNDELEV double, FLOORAREA char(3), StackLevel double, DDPFLOORSORT char(71), FLOORCODE char(20), INTERIORSPACE char(3), BLDGNAME char(30), DRAWINGNAME char(100), NAMELONG char(100), SENSITIVITY char(30), FLOORID char(60), NAMESHORT char(50), FLOORPLANLINE char(3)
    -> AttributeExposer_3
AttributeExposer_3
    ATTR_LIST = fme_feature_type,BUILDINGID,FLOORID
    -> BulkAttributeRenamer
BulkAttributeRenamer
    CASE_CHANGE_TYPE = lowercase
    ATTRCHOICE = All Attributes
    PATTERN_ACTION_DISP = Change Case
    -> gseGetBldgFloorInfo
gseGetBldgFloorInfo
    flr = @Value(floorid)
    FeatureMerger_3_Merged -> FeatureMerger [input 2]
FeatureMerger
    MERGE_TYPE = Attributes Only
    SUPPLIER_PREFIX_DUMMY = YES
    JOIN_KEYS = @Value(floorid) @Value(floorid) AUTO
    SUPPLIERS_FIRST = No
    PROCESS_DUPS = No
    IGNORE_NULLS = Yes
    MERGED -> TestFilter
    NOT_MERGED -> FeatureMerger_NotMerged_2
Note: just using bldg outline now... Apr2016
TestFilter
    DEFAULT_VALUE = <UNFILTERED>
    TEST_LIST = BOOL_OP,OR,COMPOSITE_TEST,<Unused>,TEST_CLAUSE,"TEST @Value(fme_feature_type) = FloorplanLine",FloorplanLine,BOOL_OP,OR,COMPOSITE_TEST,<Unused>,TEST_CLAUSE,"TEST @Value(fme_feature_type) = Floor_Poly",Floor_Poly,BOOL_OP,OR,COMPOSITE_TEST,<Unused>,TEST_CLAUSE,"TEST @Value(fme_feature_type) = InteriorSpace",InteriorSpace
    Floor_Poly -> Aggregator
    InteriorSpace -> gzTiltRooms
    InteriorSpace -> InsidePointReplacer
Note: No floor point Apr2016
Aggregator
    ACCUM_ATTRS_NAME = Yes
    ORDERED = No
    SEP = ,
    AGGREGATE_TYPE = Homogeneous Collection (If Possible)
    MODE = Assemble One Level
    GROUP_BY = floorid
    SUM = floorarea
    AGGREGATE -> FloorArea
FloorArea: AttributeCreator
    ATTR_LIST = fme_feature_type,FloorArea
    -> AttributeCreator_3
Note: Create FloorArea Aggregate Polygon
gzTiltRooms
    _YMAX = @Value(_ymax)
    _YMIN = @Value(_ymin)
    SPACEID = @Value(spaceid)
    MARGIN = .1
    STACKLEVEL = @Value(stacklevel)
    SPACING = 1
    tiltDemoninator = 2
    _XMAX = @Value(_xmax)
    CALCROT = @Value(calcrot)
    -> InteriorSpace_Tilt
InteriorSpace_Tilt: AttributeCreator
    ATTR_LIST = fme_feature_type,InteriorSpace_Tilt
    -> AttributeCreator_3
Note: Tilt function for interior spaces
Note: Create points for Spaces
InsidePointReplacer
    INSIDEPOINT -> InteriorSpace_Point
InteriorSpace_Point: AttributeCreator
    ATTR_LIST = fme_feature_type,InteriorSpace_Point
    -> AttributeCreator_3
FeatureMerger_NotMerged_2: Logger
    MAXFEATS = 20000
    MAXCOORDS = 20
    MESSAGE = Feature is missing floor data:
Note: Create Floor_Outline polygon
AttributeExposer
    ATTR_LIST = fme_type,fme_geometry
    -> FeatureMerger_2 [input 2]
Bufferer
    OFFSET = 1
    INTERP_SEGMENTS = 8
    GROUP_BY = floorid
    CAP_STYLE = Round
    BUFFERED -> FeatureMerger_2 [input 1]
FeatureMerger_2
    MERGE_TYPE = Attributes Only
    SUPPLIER_PREFIX_DUMMY = YES
    JOIN_KEYS = @Value(floorid) @Value(floorid) AUTO
    SUPPLIERS_FIRST = No
    PROCESS_DUPS = No
    IGNORE_NULLS = Yes
    MERGED -> Floor_Outline
Floor_Outline: AttributeCreator
    ATTR_LIST = fme_feature_type,Floor_Outline
    -> AttributeCreator_3
Note: Create floorpoint using Outline center point
GeometryReplacer
    KIND_LONG = FME Binary
    REMOVE_ATTRIBUTE = Yes
    SOURCE = @Value(_geometry)
    -> Floor_Point
Floor_Point: AttributeCreator
    ATTR_LIST = fme_feature_type,Floor_Point
    -> AttributeCreator_3
AttributeCreator_3
    ATTR_LIST = DRAWING,@Value(floorid)
    -> 3DForcer
3DForcer
    ZVALATTR = @Value($(elevName)) * 0.3048
    -> BulkAttributeRenamer_3
Note: SQL Server/Oracle
BulkAttributeRenamer_3
    CASE_CHANGE_TYPE = UPPERCASE
    ATTRCHOICE = All Attributes
    PATTERN_ACTION_DISP = Change Case
    -> gzFieldCalculator
gzFieldCalculator
    AddFieldsValues_Output_1 -> gzSourceTargetQA
gzSourceTargetQA
    SourceTargetQA_Output_1 -> gzWriteData
gzWriteData
    IgnoreErrors = False
    HASERRORS = @Value(HasErrors)
    GroupBy = @Value(FLOORID)
    gzLogWriter -> gzLog (writer GEODATABASE_SDE_4)
    gzErrorWriter -> gzError (writer GEODATABASE_SDE_4)
    gzFeatureWriter -> TruncateFirst
gzLog (writer GEODATABASE_SDE_4)
    attributes: procname char(255), loadtime date, loadname char(255), dataset char(255), completed smallint, loaduser char(255), activeflag char(255)
TruncateFirst: TestFilter
    DEFAULT_VALUE = <UNFILTERED>
    TEST_LIST = BOOL_OP,OR,COMPOSITE_TEST,<Unused>,TEST_CLAUSE,"TEST $(truncate) = Y",Y,BOOL_OP,OR,COMPOSITE_TEST,<Unused>,TEST_CLAUSE,"TEST $(truncate) = N",N
    N -> NewFeatureType (writer GEODATABASE_SDE_4)
    Y -> NewFeatureType00 (writer GEODATABASE_SDE_4)
NewFeatureType00 (writer GEODATABASE_SDE_4)
NewFeatureType (writer GEODATABASE_SDE_4)
gzError (writer GEODATABASE_SDE_4)
    attributes: procname char(255), sourcename char(255), srcidfield char(255), srcidval char(255), dataset char(255), reason char(255), erruser char(255), errtime date, activeflag char(255)

FME custom transformer gzTiltRooms
Tilt Rooms in floorplans to create a pseudo-isometric view of the rooms and floors

Parameters:
- _XMAX = @Value(_xmax)   # Xmax
- _YMAX = @Value(_ymax)   # Ymax
- _YMIN = @Value(_ymin)   # Ymin
- tiltDemoninator = 2   # Tilt = 2 will tilt 50% or y/2
- STACKLEVEL = @Value(stacklevel)   # stacklevel
- CALCROT = @Value(calcrot)   # calcrot
- SPACEID = @Value(spaceid)   # spaceid
- MARGIN = .1   # margin
- SPACING = 1   # spacing

INPUT (input)
    -> Rotation
Note: Function will rotate flat/horizontal. Add 15 degrees
Rotation: ExpressionEvaluator
    VAL_ATTR = calculated_rotation
    EXPRESSION = @Value(calcrot) + 15
    -> Rotator
Rotator
    XORIG = @Value(_xmax)
    ANGLE = @Value(calculated_rotation)
    YORIG = @Value(_ymax)
    ROTATED -> Y_Base
Note: Add 10 meters to the base of every point * stacklevel + y height
Y_Base: ExpressionEvaluator
    VAL_ATTR = _yBase
    EXPRESSION = (@Value(_ymax)  + 10 ) + (@Value(stacklevel)  * $(SPACING) * (@abs(@Value(_ymax) - @Value(_ymin))/$(tiltDemoninator)))
    -> tiltFactor
tiltFactor: ExpressionEvaluator
    VAL_ATTR = _tiltFactor
    EXPRESSION = "$(SPACING) * $(tiltDemoninator)\n\n"
    -> AttributeCreator
AttributeCreator
    ATTR_LIST = _subtracty,@Value(_ymax),_margin,$(MARGIN)
    -> TiltFeatures
TiltFeatures: PythonCaller
    NEW_ATTRIBUTES = _subtracty _yBase margin _tiltFactor
    PYTHONSOURCE:
      import fmeobjects

      debug = False
      # Template Function interface:
      def processFeature(feature):
          pass

      # Template Class Interface:
      class FeatureProcessor(object):
          def __init__(self):
              pass
          def input(self,feature):
              ### Formula is yBase + ((y - subtracty) / tiltFactor) * (1 - margin)
              yBase = float(feature.getAttribute("_yBase"))
              subtracty = float(feature.getAttribute("_subtracty"))
              tiltFactor = float(feature.getAttribute("_tiltFactor"))
              margin = float(feature.getAttribute("_margin"))
              heightPercent = 1 - margin
              if debug == True:
                  logger.logMessageString(str(yBase) + '|' + str(subtracty) + '|' +  str(tiltFactor) + '|' +  str(margin))
              parts = feature.getDonutParts()
              for part in parts:
                  coords = part.getAllCoordinates()
                  for i in xrange(len(coords)):
                      # Assume 2D geometries here
                      y = coords[i][1]
                      yDiff = y - subtracty
                      rawY = yDiff / tiltFactor
                      addY = rawY * heightPercent
                      tilt_y = yBase + addY
                      coords[i] = (coords[i][0], tilt_y)

                      if debug == True:
                          logger.logMessageString("y="+str(y))
                          logger.logMessageString("yBase="+str(yBase))
                          logger.logMessageString("rawY="+str(rawY))
                          #logger.logMessageString("yDiff="+str(yDiff))
                          #logger.logMessageString("heightPercent="+str(heightPercent))
                          #logger.logMessageString("tiltFactor="+str(tiltFactor))
                          logger.logMessageString("addY="+str(addY))
                          logger.logMessageString("tilt_y="+str(tilt_y))
                  part.resetCoords()
                  part.addCoordinates(coords)
              if len(parts) > 0:
                  feature.makeDonuts(parts)
                  del coords, parts
              self.pyoutput(feature)

          def close(self):
              pass
    PYTHONSYMBOL = FeatureProcessor
    -> GeometryValidator_3
GeometryValidator_3
    DUP_COORDS_CHECK_Z = Yes
    ARC_ENDPOINT_TOLERANCE = 0.001
    PLANAR_TOLERANCE_MODE = Custom
    CONSECUTIVE_IDENTICAL_VERTICES_2D = CONSECUTIVE_IDENTICAL_VERTICES_2D
    ISSUE_ATTR_NAME = _issues
    TYPE_REPAIR = TYPE_REPAIR
    CHECK_HOLE_TOUCHING_POLYGON = Yes
    ARC_ENDPOINT_TOLERANCE_MODE = Custom
    PLANAR_SURFACE = PLANAR_SURFACE
    PRESETS = Custom
    SELF_INTERSECTING = SELF_INTERSECTING
    PLANAR_TOLERANCE = 0.001
    REPAIR = No
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    FAILED -> Generalizer
    PASSED -> OUTPUT (output)
Generalizer
    TOLERANCE = .05
    ALG_TEXT = Douglas (Generalize)
    PRESERVE = No
    -> SpikeRemover
SpikeRemover
    SPIKEANGLE = 3
    UNCHANGED -> GeometryValidator_2
    CHANGED -> GeometryValidator_2
GeometryValidator_2
    DUP_COORDS_CHECK_Z = No
    CONSECUTIVE_IDENTICAL_VERTICES_2D = CONSECUTIVE_IDENTICAL_VERTICES_2D
    ISSUE_ATTR_NAME = _issues
    CHECK_HOLE_TOUCHING_POLYGON = Yes
    PRESETS = Custom
    SELF_INTERSECTING = SELF_INTERSECTING
    REPAIR = Yes
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    PASSED -> OUTPUT (output)
    REPAIRED -> OUTPUT (output)
    FAILED -> GeometryValidator_2_Failed
OUTPUT (output)
GeometryValidator_2_Failed: Logger
    MAXFEATS = 20
    MAXCOORDS = 20
    MESSAGE = Feature is:

FME custom transformer gzBuildingAngle

Parameters:
- BUILDINGID =   # Enter the Building ID

INPUT (input)
    -> Chopper_2
    -> FeatureMerger_3 [input 1]
Chopper_2
    MAX = 2
    CHOPPED -> LengthCalculator_2
LengthCalculator_2
    DIM = 2
    LEN_ATTR = _length
    MULT = 1
    -> StatisticsCalculator_2
StatisticsCalculator_2
    MAX_ATTR = _max
    MEAN_ATTR = _mean
    MODE_ATTR = _mode
    COUNT_ATTR = _count
    STATS_ATTR = _length
    STDEV_ATTR = _stdev
    SUM_ATTR = _sum
    PASS_THROUGH = Yes
    NUMERIC_ATTR = _numeric_count
    MIN_ATTR = _min
    MEDIAN_ATTR = _median
    RANGE_ATTR = _range
    STATISTICS -> TestFilter_6
TestFilter_6
    DEFAULT_VALUE = <UNFILTERED>
    TEST_LIST = BOOL_OP,OR,COMPOSITE_TEST,<Unused>,TEST_CLAUSE,"TEST ""@Value(_length)"" = ""@Value(_max)""",_length = _max
    _length = _max -> CoordinateExtractor_4
CoordinateExtractor_4
    Y_ATTR = _y1
    Z_DEFAULT = -9999
    X_ATTR = _x1
    IND = 0
    Z_ATTR = _z
    -> CoordinateExtractor_6
CoordinateExtractor_6
    Y_ATTR = _y2
    Z_DEFAULT = -9999
    X_ATTR = _x2
    IND = 1
    Z_ATTR = _z
    -> TestFilter_4
TestFilter_4
    DEFAULT_VALUE = <UNFILTERED>
    TEST_LIST = BOOL_OP,OR,COMPOSITE_TEST,<Unused>,TEST_CLAUSE,"TEST ""@Value(_y2)"" >= ""@Value(_y1)""",_y2 >= _y1
    _y2 >= _y1 -> ExpressionEvaluator_7
    <UNFILTERED> -> ExpressionEvaluator_4
Note: Calculate angle of the longest side
ExpressionEvaluator_7
    VAL_ATTR = _angle
    EXPRESSION = @atan2(@Value(_x1)-@Value(_x2),@Value(_y1)-@Value(_y2))*180.0/(22/7.0)
    -> ExpressionEvaluator_8
ExpressionEvaluator_4
    VAL_ATTR = _angle
    EXPRESSION = @atan2(@Value(_x2)-@Value(_x1),@Value(_y2)-@Value(_y1))*180.0/(22/7.0)
    -> ExpressionEvaluator_8
ExpressionEvaluator_8
    VAL_ATTR = _angle
    EXPRESSION = @Value(_angle) + 90.0
    -> TestFilter_5
TestFilter_5
    DEFAULT_VALUE = <UNFILTERED>
    TEST_LIST = BOOL_OP,OR,COMPOSITE_TEST,<Unused>,TEST_CLAUSE,"TEST ""@Value(_angle)"" > ""180.0""",_angle > 180.0
    _angle > 180.0 -> ExpressionEvaluator_10
    <UNFILTERED> -> Sorter_2
ExpressionEvaluator_10
    VAL_ATTR = _angle
    EXPRESSION = @Value(_angle) -180.0
    -> Sorter_2
Sorter_2
    SORT_PARM = _length NUMERIC DESCENDING
    SORTED -> FeatureMerger_3 [input 2]
FeatureMerger_3
    MERGE_TYPE = Attributes Only
    BUILD_INCOMPLETE = No
    REFERATTR = $(BUILDINGID)
    REFEEATTR = $(BUILDINGID)
    PROCESS_DUPS = No
    COMPLETE -> GeometryExtractor_2
GeometryExtractor_2
    KIND_LONG = FME Binary
    ATTR = _geometry
    -> CenterOfGravityReplacer
CenterOfGravityReplacer
    CENTEROFGRAVITY -> CoordinateExtractor_3
CoordinateExtractor_3
    Y_ATTR = YCENTER
    Z_DEFAULT = -9999
    X_ATTR = XCENTER
    IND = 0
    Z_ATTR = _z
    -> GeometryReplacer
GeometryReplacer
    KIND_LONG = FME Binary
    ATTR = _geometry
    -> AttributeCreator
Note: Calculate X and Y Center Point
AttributeCreator
    ATTR_LIST = MODANGLE,0,SPACING,50,MARGIN,.2,HULLROT,@Value(_angle)
    -> OUTPUT (output)
OUTPUT (output)

FME custom transformer gzSetupExtract

INPUT (input)
    -> AttributeExposer
AttributeExposer
    ATTR_LIST = fme_feature_type_name
    -> PythonCaller
PythonCaller
    NEW_ATTRIBUTES = WhereClause *
    PYTHONSOURCE:
      import fmeobjects


      # Template Function interface:
      def processFeature(feature):
          pass

      # Template Class Interface:
      class FeatureProcessor(object):
          def __init__(self):
              pass
          def input(self,feature):
              whereClause = ""
              featType = feature.getAttribute("fme_feature_type_name")
              for sourceDataset in sourceDatasets:
                  sourceName = sourceDataset.getAttributeNode("sourceName").nodeValue
                  if debug == True:
                      logger.logMessageString("gz sources=" + featType + "|" + sourceName)
                  if sourceName == featType:
                      whereClause = getWhereClause(featType)
                      if debug == True:
                          logger.logMessageString("gz Where=" + whereClause)
                      feature.setAttribute("WhereClause",whereClause)
                      self.pyoutput(feature)

          def close(self):
              pass
    PYTHONSYMBOL = FeatureProcessor
    -> OUTPUT (output)
OUTPUT (output)

FME custom transformer gseGetBldgFloorInfo

Parameters:
- flr =   # Floor ID

TestFilter_2_Input (input)
    -> AttributeExposer
AttributeExposer
    ATTR_LIST = floorid,buildingid,bldg,schelev,fme_feature_type,floor,siteid,calcrot,floor_name,floor_level,stacklevel
    -> BulkAttributeRenamer
BulkAttributeRenamer
    CASE_CHANGE_TYPE = lowercase
    ATTRCHOICE = All Attributes
    PATTERN_ACTION_DISP = Change Case
    -> TestFilter_2
TestFilter_2
    DEFAULT_VALUE = <UNFILTERED>
    TEST_LIST = BOOL_OP,OR,COMPOSITE_TEST,<Unused>,TEST_CLAUSE,"TEST @Value(fme_feature_type) = AllFloors",AllFloors,BOOL_OP,OR,COMPOSITE_TEST,<Unused>,TEST_CLAUSE,"TEST @Value(fme_feature_type) = FloorPageTemplate",FloorPageTemplate
    FloorPageTemplate -> BoundsExtractor
    AllFloors -> FeatureMerger_3 [input 1]
BoundsExtractor
    ZMIN = _zmin
    ZMAX = _zmax
    XMIN = _xmin
    XMAX = _xmax
    YMIN = _ymin
    YMAX = _ymax
    -> LengthCalculator
LengthCalculator
    DIM = 2
    LEN_ATTR = _bldg_outline_length
    MULT = 1
    -> FeatureMerger_3 [input 2]
FeatureMerger_3
    MERGE_TYPE = Attributes Only
    SUPPLIER_PREFIX_DUMMY = YES
    JOIN_KEYS = @Value(floor) @Value(floor) AUTO
    SUPPLIERS_FIRST = No
    PROCESS_DUPS = No
    IGNORE_NULLS = Yes
    MERGED -> FeatureMerger_3_Merged (output)
FeatureMerger_3_Merged (output)
