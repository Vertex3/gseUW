FME workspace gseFloorplanDerivefdgb.fmw
Title: GizintaLoader
Description: First Beta release of Gizinta for FME
Usage: Add the xml file and other parameters
Requirements: test
History: 31/10/2013,support@Gizinta.com,First Draft
Legal terms conditions: This work is licensed under the Creative Commons Attribution-ShareAlike 3.0 Unported License.
Startup Python:
      import xml.dom.minidom
      import os
      import sys
      import time
      import fmeobjects

      ospath = FME_MacroValues['FME_MF_DIR']
      print ospath
      if ospath not in sys.path:
          sys.path.append(ospath)
      import gzfme

      ErrorUniqueID = "ErrorUniqueID"
      ErrorRequiredValue = "ErrorRequiredValue"
      ErrorValueMap = "ErrorValueMap"
      Errors = False

      debug = gzfme.setDebug(FME_MacroValues['gzDebug'])
      logger = fmeobjects.FMELogFile()
      gzfme.logger = logger
Shutdown Python:
      import fmeobjects, gzfme

      gzfme.shutdown(Errors,str(FME_MacroValues['IgnoreErrors']),FME_TotalFeaturesWritten,FME_MacroValues)

      del Errors
      del ErrorUniqueID
      del ErrorRequiredValue
      del ErrorValueMap
      del debug
      del logger
      gzfme.logger = None

Parameters:
- ProductionConnectionFile = C:\Apps\Gizinta\gseUW\ETL\serverConfig\GIS Production.sde   # Enter the path and name of the Production SDE Database connection file
- GizintaProject = C:\Apps\Gizinta\gseUW\ETL\config\fpDerivePlaylist.xml   # Select the Gizinta Xml File to use
- SourceFieldQA = False   # Choose whether to perform QA on Source Fields
- TargetFieldQA = True   # Choose whether to perform QA on Target Fields
- IgnoreErrors = False   # Ignore Errors and continue
- SourceDatasetTypes = GDBDataset   # Enter the Gizinta Source Dataset Type
- flr = UWS_1002_01   # Enter the FLOORID
- bldg = UWS_1002   # BuildingID
- gzDebug = False   # Enable gzDebug (True/False)
- LOG_FILE =   # Log File
- FEATURE_TYPES = InteriorSpace_Tilt FloorplanLine InteriorSpace Floor_Outline Floor_Point Floor_Poly FloorplanLine_Publish Floor_Area InteriorSpace_Point   # " " Feature Types to Write
- FEATURE_TYPES_READ = Floor_Poly InteriorSpace FloorplanLine
- FEATURE_TYPES_PROD = Building_Outline_Point Building_Outline_Tilt Active_Floor Floor_Level
- truncate = Y   # Truncate before load option
- DestDataset_FILEGDB = R:\Apps\Gizinta\uwprod.gdb   # Destination Geodatabase
- SourceDataset_FILEGDB = R:\Apps\Gizinta\uwprod.gdb   # Source Geodatabase

Readers:
- FILEGDB_1: FILEGDB from $(SourceDataset_FILEGDB)
- FILEGDB_2: FILEGDB from $(SourceDataset_FILEGDB)
- FILEGDB_3: FILEGDB from $(SourceDataset_FILEGDB)

Writers:
- FILEGDB_4: FILEGDB to $(DestDataset_FILEGDB)

gzLog (reader FILEGDB_2)
    attributes: OBJECTID objectid, PROCNAME text(255), LOADTIME date, LOADNAME text(255), DATASET text(255), COMPLETED smallint, LOADUSER text(255), ACTIVEFLAG text(255), SRCIDVAL text(255), ERRUSER text(255), ERRTIME date, SRCIDFIELD text(255), REASON text(255), SOURCENAME text(255)
    -> AttributeExposer_2
AttributeExposer_2
    ATTR_LIST = DRAWING,fme_feature_type,SPACEID,spaceid,floorid,buildingid,FLOORID,BUILDINGID,FLOOR_AREA
    -> TestIDs
TestIDs: Tester
    TEST_MODE = Automatic
    TEST_DESCRIPTION = ""
    BOOL_OP = OR
    TEST_CLAUSE:
      TEST floorid ATTRIBUTE_IS_MISSING ""
      TEST floorid ATTRIBUTE_VALUE_NULL ""
    PASSED -> AttributeCopier
AttributeCopier
    ATTR_LIST = FLOORID,floorid,"",BUILDINGID,buildingid,"",SPACEID,spaceid,""
    -> TestFeatureTypes
TestFeatureTypes: Tester
    TEST_MODE = Automatic
    TEST_DESCRIPTION = ""
    BOOL_OP = OR
    TEST_CLAUSE = TEST $(FEATURE_TYPES_READ) CONTAINS @Value(fme_feature_type)
    PASSED -> TestFLOORID
TestFLOORID: Tester
    TEST_MODE = Automatic
    TEST_DESCRIPTION = ""
    BOOL_OP = OR
    TEST_CLAUSE = TEST @Value(floorid) = $(flr)
    PASSED -> BulkAttributeRenamer_2
BulkAttributeRenamer_2
    CASE_CHANGE_TYPE = lowercase
    ATTRCHOICE = All Attributes
    PATTERN_ACTION_DISP = Change Case
    -> FeatureMerger [input 1]
gzLog (reader FILEGDB_3)
    attributes: OBJECTID objectid, PROCNAME text(255), LOADTIME date, LOADNAME text(255), DATASET text(255), COMPLETED smallint, LOADUSER text(255), ACTIVEFLAG text(255), SRCIDVAL text(255), ERRUSER text(255), ERRTIME date, SRCIDFIELD text(255), REASON text(255), SOURCENAME text(255)
    -> AttributeExposer_3
AttributeExposer_3
    ATTR_LIST = DRAWING,fme_feature_type,buildingid,floor,TILTHEIGHT,SPACING,MARGIN
    -> setupIDs
Note: setup building and floor data
setupIDs: AttributeCreator
    ATTR_LIST = floorid,$(flr),bldg,$(bldg)
    -> BulkAttributeRenamer
BulkAttributeRenamer
    CASE_CHANGE_TYPE = lowercase
    ATTRCHOICE = All Attributes
    PATTERN_ACTION_DISP = Change Case
    -> gseGetBldgFloorInfo
gseGetBldgFloorInfo
    BLDG = $(bldg)
    flr = $(flr)
    FLOORID = @Value(floorid)
    BUILDINGID = @Value(buildingid)
    FeatureMerger_3_Merged -> FeatureMerger [input 2]
FeatureMerger
    PROCESS_DUPS = No
    MERGE_TYPE = Attributes Only
    SUPPLIERS_FIRST = No
    JOIN_KEYS = @Value(floorid) @Value(floorid) AUTO
    SUPPLIER_PREFIX_DUMMY = YES
    MERGED -> TestFilter
TestFilter
    TEST_LIST = BOOL_OP,OR,COMPOSITE_TEST,<Unused>,TEST_CLAUSE,"TEST @Value(fme_feature_type) = FloorplanLine",FloorplanLine,BOOL_OP,OR,COMPOSITE_TEST,<Unused>,TEST_CLAUSE,"TEST @Value(fme_feature_type) = InteriorSpace",InteriorSpace,BOOL_OP,OR,COMPOSITE_TEST,<Unused>,TEST_CLAUSE,"TEST @Value(fme_feature_type) = Floor_Poly",Floor_Poly
    DEFAULT_VALUE = <UNFILTERED>
    InteriorSpace -> InsidePointReplacer
    InteriorSpace -> gzTiltRooms
    FloorplanLine -> HullAccumulator
    FloorplanLine -> FeatureMerger_2 [input 2]
    Floor_Poly -> Aggregator
    Floor_Poly -> GeometryReplacer
Note: Create Floor_Outline polygon
HullAccumulator
    GROUP_BY = floorid
    HULLTYPE_PARAM = Convex ()
    HULL -> Bufferer
Bufferer
    INTERP_SEGMENTS = 8
    OFFSET = 1
    CAP_STYLE = Round
    BUFFERED -> FeatureMerger_2 [input 1]
FeatureMerger_2
    PROCESS_DUPS = No
    MERGE_TYPE = Attributes Only
    SUPPLIERS_FIRST = No
    JOIN_KEYS = @Value(floorid) @Value(floorid) AUTO
    SUPPLIER_PREFIX_DUMMY = YES
    MERGED -> Floor_Outline
Floor_Outline: AttributeCreator
    ATTR_LIST = fme_feature_type,Floor_Outline
    -> AttributeCreator_3
gzTiltRooms
    pFLOORID = @Value(floorid)
    tiltHeight = 2
    -> gzFixIntersections
gzFixIntersections
    Feature_Type = InteriorSpace
    Tolerance = 0.001
    UniqueIDName = @Value(spaceid)
    -> InteriorSpace_Tilt
InteriorSpace_Tilt: AttributeCreator
    ATTR_LIST = fme_feature_type,InteriorSpace_Tilt
    -> AttributeCreator_3
Note: Tilt function for interior spaces
InsidePointReplacer
    INSIDEPOINT -> InteriorSpace_Point
InteriorSpace_Point: AttributeCreator
    ATTR_LIST = fme_feature_type,InteriorSpace_Point
    -> AttributeCreator_3
Note: Create points for Spaces
GeometryReplacer
    SOURCE = @Value(_geometry)
    REMOVE_ATTRIBUTE = No
    KIND_LONG = FME Binary
    -> Floor_Point
Floor_Point: AttributeCreator
    ATTR_LIST = fme_feature_type,Floor_Point
    -> AttributeCreator_3
Note: Create floorpoint using Outline center point
Note: Create Floor_Area Aggregate Polygon
Aggregator
    GROUP_BY = floorid
    MODE = Assemble One Level
    ACCUM_ATTRS_NAME = Yes
    SEP = ,
    SUM = floor_area
    AGGREGATE_TYPE = Homogeneous Collection (If Possible)
    ORDERED = No
    AGGREGATE -> Floor_Area
Floor_Area: AttributeCreator
    ATTR_LIST = fme_feature_type,Floor_Area
    -> AttributeCreator_3
AttributeCreator_3
    ATTR_LIST = DRAWING,$(flr)
    -> BulkAttributeRenamer_3
BulkAttributeRenamer_3
    CASE_CHANGE_TYPE = UPPERCASE
    ATTRCHOICE = All Attributes
    PATTERN_ACTION_DISP = Change Case
    -> gzFieldCalculator
gzFieldCalculator
    AddFieldsValues_Output_1 -> gzSourceTargetQA
gzSourceTargetQA
    SourceTargetQA_Output_1 -> gzWriteData
gzWriteData
    IgnoreErrors = False
    GroupBy = @Value(FLOORID)
    HASERRORS = @Value(HasErrors)
    gzFeatureWriter -> TruncateFirst
    gzLogWriter -> gzLog (writer FILEGDB_4)
    gzErrorWriter -> gzError (writer FILEGDB_4)
gzLog (writer FILEGDB_4)
    attributes: OBJECTID objectid, PROCNAME text(255), LOADTIME date, LOADNAME text(255), DATASET text(255), COMPLETED smallint, LOADUSER text(255), ACTIVEFLAG text(255)
TruncateFirst: TestFilter
    TEST_LIST = BOOL_OP,OR,COMPOSITE_TEST,<Unused>,TEST_CLAUSE,"TEST $(truncate) = Y",Y,BOOL_OP,OR,COMPOSITE_TEST,<Unused>,TEST_CLAUSE,"TEST $(truncate) = N",N
    DEFAULT_VALUE = <UNFILTERED>
    Y -> NewFeatureType00 (writer FILEGDB_4)
    N -> NewFeatureType (writer FILEGDB_4)
NewFeatureType00 (writer FILEGDB_4)
NewFeatureType (writer FILEGDB_4)
gzError (writer FILEGDB_4)
    attributes: OBJECTID objectid, PROCNAME text(255), SOURCENAME text(255), SRCIDFIELD text(255), SRCIDVAL text(255), DATASET text(255), REASON text(255), ERRUSER text(255), ERRTIME date, ACTIVEFLAG text(255)

FME custom transformer gseGetBldgFloorInfo

Parameters:
- flr =   # Floor ID
- BUILDINGID = @Value(buildingid)   # buildingid
- BLDG = @Value(bldg)   # bldg
- FLOORID = @Value(floorid)   # floorid

TestFilter_2_Input (input)
    -> AttributeExposer
AttributeExposer
    ATTR_LIST = floorid,buildingid,bldg,schelev,fme_feature_type,floor,siteid,calcrot,floor_name,floor_level
    -> TestFilter_2
TestFilter_2
    TEST_LIST = BOOL_OP,OR,COMPOSITE_TEST,<Unused>,TEST_CLAUSE,"TEST @Value(fme_feature_type) = Building_Outline_Tilt",Building_Outline_Tilt,BOOL_OP,OR,COMPOSITE_TEST,<Unused>,TEST_CLAUSE,"TEST @Value(fme_feature_type) = Building_Outline_Point",Building_Outline_Point,BOOL_OP,OR,COMPOSITE_TEST,<Unused>,TEST_CLAUSE,"TEST @Value(fme_feature_type) = Active_Floor",Active_Floor,BOOL_OP,OR,COMPOSITE_TEST,<Unused>,TEST_CLAUSE,"TEST @Value(fme_feature_type) = Floor_Level",Floor_Level
    DEFAULT_VALUE = <UNFILTERED>
    Floor_Level -> FeatureMerger_3 [input 2]
    Building_Outline_Tilt -> BoundsExtractor
    Active_Floor -> TestFilterBldg
    Building_Outline_Point -> GeometryExtractor
BoundsExtractor
    YMIN = _ymin
    ZMIN = _zmin
    XMIN = _xmin
    XMAX = _xmax
    ZMAX = _zmax
    YMAX = _ymax
    -> LengthCalculator
LengthCalculator
    LEN_ATTR = _bldg_outline_length
    MULT = 1
    DIM = 2
    -> FeatureMerger_4 [input 1]
GeometryExtractor
    ATTR = _geometry
    KIND_LONG = FME Binary
    -> FeatureMerger_4 [input 2]
FeatureMerger_4
    PROCESS_DUPS = No
    MERGE_TYPE = Attributes Only
    SUPPLIERS_FIRST = No
    JOIN_KEYS = @Value(buildingid) @Value(buildingid) AUTO
    SUPPLIER_PREFIX_DUMMY = YES
    MERGED -> FeatureMerger_2 [input 1]
TestFilterBldg
    TEST_LIST = BOOL_OP,OR,COMPOSITE_TEST,<Unused>,TEST_CLAUSE,"TEST $(flr) BEGINS_WITH @Value(buildingid)",bldgid
    DEFAULT_VALUE = <UNFILTERED>
    bldgid -> ListBuilder_2
ListBuilder_2
    LIST_NAME = _floors
    GRP_BY = buildingid
    -> sortScheleve
sortScheleve: ListSorter
    TYPE = Numeric
    SRC_LIST = _floors{}.schelev
    ORDER = Increasing
    -> ListExploder_2
ListExploder_2
    INDEX_ATTR = _stack_index
    MODE = List Elements and Original Attributes
    LIST_ATTR = _floors{}
    LIST_FOUND -> Tester_2
Tester_2
    TEST_MODE = Automatic
    TEST_DESCRIPTION = ""
    BOOL_OP = OR
    TEST_CLAUSE = TEST @Value(floorid) = $(flr)
    PASSED -> AttributeCopier
AttributeCopier
    ATTR_LIST = _stack_index,stacklevel,""
    -> FeatureMerger_2 [input 2]
FeatureMerger_2
    PROCESS_DUPS = No
    MERGE_TYPE = Attributes Only
    SUPPLIERS_FIRST = No
    JOIN_KEYS = @Value(buildingid) @Value(buildingid) AUTO
    SUPPLIER_PREFIX_DUMMY = YES
    MERGED -> FeatureMerger_3 [input 1]
FeatureMerger_3
    PROCESS_DUPS = No
    MERGE_TYPE = Attributes Only
    SUPPLIERS_FIRST = No
    JOIN_KEYS = @Value(floor) @Value(floor) AUTO
    SUPPLIER_PREFIX_DUMMY = YES
    MERGED -> FeatureMerger_3_Merged (output)
FeatureMerger_3_Merged (output)

FME custom transformer gzTiltRooms
Tilt Rooms in floorplans to create a pseudo-isometric view of the rooms and floors

Parameters:
- pFLOORID = UWS_1002_02   # Enter the Floor ID
- tiltHeight = 2   # Tilt height - 2 will tilt 50%

INPUT (input)
    -> AttributeCopier_3
AttributeCopier_3
    ATTR_LIST = stacklevel,_stack_index,STACKLEVEL,_stack_index
    -> AttributeCopier_3_Output
    -> Rotation
Note: Function will rotate flat/horizontal. Add 15 degrees
Rotation: ExpressionEvaluator
    VAL_ATTR = CALCULATED_ROTATION
    EXPRESSION = @Value(calcrot) + 15
    -> Rotator
Rotator
    YORIG = @Value(_ymin)
    ANGLE = @Value(CALCULATED_ROTATION)
    XORIG = @Value(_xmin)
    ROTATED -> Y_Base
Note: Add 40 meters to the base of every point * stacklevel + building height
Y_Base: ExpressionEvaluator
    VAL_ATTR = _yBase
    EXPRESSION = @Value(_ymin) + (@Value(stacklevel)  * @Value(spacing)  * 30 * (@Value(_bldg_outline_length) / @abs(@Value(_ymax) - @Value(_ymin))/$(tiltHeight)))
    -> tiltFactor
Note: height reduction 2 * spacing=1 will be 50% tilted
tiltFactor: ExpressionEvaluator
    VAL_ATTR = _tiltFactor
    EXPRESSION = "@Value(spacing) * $(tiltHeight)\n\n"
    -> Chopper
Chopper
    MAX = 1
    CHOPPED -> CoordinateExtractor
CoordinateExtractor
    Y_ATTR = _y
    X_ATTR = _x
    Z_DEFAULT = -9999
    Z_ATTR = _z
    IND = 0
    -> tilt_y
Note: calc tilted y value for each point
tilt_y: ExpressionEvaluator
    VAL_ATTR = _tiltY
    EXPRESSION = @Value(_yBase) + ((@Value(_y) - @Value(_ymin)) / @Value(_tiltFactor)) * (1 - @Value(margin))
    -> 2DPointReplacer
2DPointReplacer
    XVALATTR = @Value(_x)
    YVALATTR = @Value(_tiltY)
    POINT -> PointConnector
PointConnector
    BREAKATTR = spaceid
    POLYGON -> GeometryCoercer_2
    LINE -> GeometryCoercer_2
GeometryCoercer_2
    CHECKZ = No
    KIND = fme_polygon
    COERCED -> SelfIntersectChecker_2
SelfIntersectChecker_2
    SelfIntersecting -> Logger_SelfIntersecting
    NotSelfIntersecting -> OUTPUT (output)
OUTPUT (output)
Logger_SelfIntersecting
    MESSAGE = Feature is:
    MAXFEATS = 20
    MAXCOORDS = 20
AttributeCopier_3_Output: Inspector [off]

FME custom transformer gzSetupExtract

INPUT (input)
    -> AttributeExposer
AttributeExposer
    ATTR_LIST = fme_feature_type_name
    -> PythonCaller
PythonCaller
    PYTHONSOURCE:
      import fmeobjects


      # Template Function interface:
      def processFeature(feature):
          pass

      # Template Class Interface:
      class FeatureProcessor(object):
          def __init__(self):
              pass
          def input(self,feature):
              whereClause = ""
              featType = feature.getAttribute("fme_feature_type_name")
              for sourceDataset in sourceDatasets:
                  sourceName = sourceDataset.getAttributeNode("sourceName").nodeValue
                  if debug == True:
                      logger.logMessageString("gz sources=" + featType + "|" + sourceName)
                  if sourceName == featType:
                      whereClause = getWhereClause(featType)
                      if debug == True:
                          logger.logMessageString("gz Where=" + whereClause)
                      feature.setAttribute("WhereClause",whereClause)
                      self.pyoutput(feature)

          def close(self):
              pass
    PYTHONSYMBOL = FeatureProcessor
    NEW_ATTRIBUTES = WhereClause *
    -> OUTPUT (output)
OUTPUT (output)

FME custom transformer gzBuildingAngle

Parameters:
- BUILDINGID =   # Enter the Building ID

INPUT (input)
    -> Chopper_2
    -> FeatureMerger_3 [input 1]
Chopper_2
    MAX = 2
    CHOPPED -> LengthCalculator_2
LengthCalculator_2
    LEN_ATTR = _length
    MULT = 1
    DIM = 2
    -> StatisticsCalculator_2
StatisticsCalculator_2
    STATS_ATTR = _length
    PASS_THROUGH = Yes
    MAX_ATTR = _max
    RANGE_ATTR = _range
    SUM_ATTR = _sum
    COUNT_ATTR = _count
    NUMERIC_ATTR = _numeric_count
    STDEV_ATTR = _stdev
    MODE_ATTR = _mode
    MEDIAN_ATTR = _median
    MIN_ATTR = _min
    MEAN_ATTR = _mean
    STATISTICS -> TestFilter_6
TestFilter_6
    TEST_LIST = BOOL_OP,OR,COMPOSITE_TEST,<Unused>,TEST_CLAUSE,"TEST ""@Value(_length)"" = ""@Value(_max)""",_length = _max
    DEFAULT_VALUE = <UNFILTERED>
    _length = _max -> CoordinateExtractor_4
CoordinateExtractor_4
    Y_ATTR = _y1
    X_ATTR = _x1
    Z_DEFAULT = -9999
    Z_ATTR = _z
    IND = 0
    -> CoordinateExtractor_6
CoordinateExtractor_6
    Y_ATTR = _y2
    X_ATTR = _x2
    Z_DEFAULT = -9999
    Z_ATTR = _z
    IND = 1
    -> TestFilter_4
TestFilter_4
    TEST_LIST = BOOL_OP,OR,COMPOSITE_TEST,<Unused>,TEST_CLAUSE,"TEST ""@Value(_y2)"" >= ""@Value(_y1)""",_y2 >= _y1
    DEFAULT_VALUE = <UNFILTERED>
    _y2 >= _y1 -> ExpressionEvaluator_7
    <UNFILTERED> -> ExpressionEvaluator_4
Note: Calculate angle of the longest side
ExpressionEvaluator_7
    VAL_ATTR = _angle
    EXPRESSION = @atan2(@Value(_x1)-@Value(_x2),@Value(_y1)-@Value(_y2))*180.0/(22/7.0)
    -> ExpressionEvaluator_8
ExpressionEvaluator_4
    VAL_ATTR = _angle
    EXPRESSION = @atan2(@Value(_x2)-@Value(_x1),@Value(_y2)-@Value(_y1))*180.0/(22/7.0)
    -> ExpressionEvaluator_8
ExpressionEvaluator_8
    VAL_ATTR = _angle
    EXPRESSION = @Value(_angle) + 90.0
    -> TestFilter_5
TestFilter_5
    TEST_LIST = BOOL_OP,OR,COMPOSITE_TEST,<Unused>,TEST_CLAUSE,"TEST ""@Value(_angle)"" > ""180.0""",_angle > 180.0
    DEFAULT_VALUE = <UNFILTERED>
    _angle > 180.0 -> ExpressionEvaluator_10
    <UNFILTERED> -> Sorter_2
ExpressionEvaluator_10
    VAL_ATTR = _angle
    EXPRESSION = @Value(_angle) -180.0
    -> Sorter_2
Sorter_2
    SORT_PARM = _length NUMERIC DESCENDING
    SORTED -> FeatureMerger_3 [input 2]
FeatureMerger_3
    BUILD_INCOMPLETE = No
    PROCESS_DUPS = No
    MERGE_TYPE = Attributes Only
    REFERATTR = $(BUILDINGID)
    REFEEATTR = $(BUILDINGID)
    COMPLETE -> GeometryExtractor_2
GeometryExtractor_2
    ATTR = _geometry
    KIND_LONG = FME Binary
    -> CenterOfGravityReplacer
CenterOfGravityReplacer
    CENTEROFGRAVITY -> CoordinateExtractor_3
CoordinateExtractor_3
    Y_ATTR = YCENTER
    X_ATTR = XCENTER
    Z_DEFAULT = -9999
    Z_ATTR = _z
    IND = 0
    -> GeometryReplacer
GeometryReplacer
    ATTR = _geometry
    KIND_LONG = FME Binary
    -> AttributeCreator
Note: Calculate X and Y Center Point
AttributeCreator
    ATTR_LIST = MODANGLE,0,SPACING,50,MARGIN,.2,HULLROT,@Value(_angle)
    -> OUTPUT (output)
OUTPUT (output)

FME custom transformer gzFixIntersections

Parameters:
- Tolerance = 0.001   # Generalization tolerance
- UniqueIDName = SPACEID   # UniqueID field name for polygons
- Feature_Type = InteriorSpace_All   # Feature Type to process

INPUT (input)
    -> AttributeExposer
AttributeExposer
    ATTR_LIST = fme_feature_type,DRAWING,BUILDINGID,FLOORID
    -> StringReplacer
StringReplacer
    SRC_ATTRS = fme_feature_type
    REGEXP = no
    CASE = no
    NO_MATCH = _FME_NO_OP_
    FIND_TEXT = DBO.
    -> Tester
Tester
    TEST_MODE = Automatic
    TEST_DESCRIPTION = ""
    BOOL_OP = OR
    TEST_CLAUSE = TEST @Value(fme_feature_type) = $(Feature_Type)
    PASSED -> Generalizer
Generalizer
    ALG_TEXT = Douglas (Generalize)
    PRESERVE = No
    TOLERANCE = $(Tolerance)
    -> GeometryValidator
GeometryValidator
    CHECK_HOLE_TOUCHING_POLYGON = No
    DUP_COORDS_CHECK_Z = Yes
    NULL_REMOVAL = NULL_REMOVAL
    SELF_INTERSECTING = SELF_INTERSECTING
    PRESETS = Custom
    ARC_ENDPOINT_TOLERANCE_MODE = Auto
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%""%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    REPAIR = Yes
    ISSUE_ATTR_NAME = _issues
    PLANAR_TOLERANCE_MODE = Auto
    NAN_REMOVAL = NAN_REMOVAL
    CONSECUTIVE_IDENTICAL_VERTICES_2D = CONSECUTIVE_IDENTICAL_VERTICES_2D
    PASSED -> GeometryCoercer_2
    REPAIRED -> GeometryCoercer_2
GeometryCoercer_2
    CHECKZ = No
    KIND = fme_polygon
    COERCED -> SelfIntersectChecker_2
SelfIntersectChecker_2
    SelfIntersecting -> Logger_SelfIntersecting
    NotSelfIntersecting -> OUTPUT (output)
OUTPUT (output)
Logger_SelfIntersecting
    MESSAGE = Feature is self-intersecting:
    MAXFEATS = 100
    MAXCOORDS = 20

FME custom transformer SelfIntersectChecker
Separates self-intersecting features from the rest of input. This custom transformer does not change the geometry of self-intersecting features. If you want to remove self-intersections, try the " SelfIntersector " transformer.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Input (input)
    -> PartCounter
PartCounter
    COUNT_ATTR = _part_count1
    RECURSIVE_PARAM = No
    -> COUNTER
COUNTER: Counter
    SCOPE = Local
    START = 0
    DOMAIN = counter
    CNT_ATTR = _selfID
    -> GeometryExtractor
GeometryExtractor
    OGCVERSION = 1.2
    ATTR = _geometry
    KIND_LONG = OGC Well Known Text
    -> SelfIntersector
SelfIntersector
    SEG_ATTR = _segments
    SELF_INTERSECTED -> DuplicateRemover
DuplicateRemover
    KEYATTR = _selfID
    UNIQUE -> TESTER
TESTER: Tester
    TEST_MODE = NUMERIC
    BOOL_OP = OR
    TEST_LIST = &_segments,>,1
    TEST_CLAUSE = TEST @Value(_segments) > 1
    FAILED -> PartCounter_2
    PASSED -> GeometryReplacer
PartCounter_2
    COUNT_ATTR = _part_count2
    RECURSIVE_PARAM = No
    -> TESTER_2
TESTER_2: Tester
    TEST_MODE = Automatic
    BOOL_OP = OR
    TEST_LIST = &_part_count1,=,&_part_count2
    TEST_CLAUSE = TEST @Value(_part_count1) = @Value(_part_count2)
    PASSED -> ATTRIBUTEREMOVER
    FAILED -> GeometryReplacer
ATTRIBUTEREMOVER: AttributeRemover
    REMOVE_ATTRS = _selfID,_geometry,_segments
    -> NotSelfIntersecting (output)
NotSelfIntersecting (output)
GeometryReplacer
    ATTR = _geometry
    KIND_LONG = OGC Well Known Text
    -> ATTRIBUTEREMOVER_2
ATTRIBUTEREMOVER_2: AttributeRemover
    REMOVE_ATTRS = _selfID,_geometry,_segments
    -> SelfIntersecting (output)
SelfIntersecting (output)
