FME workspace gseFloorplanLoader.fmw
Title: GizintaLoader
Description: First Beta release of Gizinta for FME
Usage: Add the xml file and other parameters
Requirements: test
History: 31/10/2013,support@Gizinta.com,First Draft
Legal terms conditions: This work is licensed under the Creative Commons Attribution-ShareAlike 3.0 Unported License.
Startup Python:
      import xml.dom.minidom
      import os
      import sys
      import time
      import fmeobjects

      ospath = FME_MacroValues['FME_MF_DIR']
      print ospath
      if ospath not in sys.path:
          sys.path.append(ospath)
      import gzfme

      ErrorUniqueID = "ErrorUniqueID"
      ErrorRequiredValue = "ErrorRequiredValue"
      ErrorValueMap = "ErrorValueMap"
      Errors = False

      debug = gzfme.setDebug(FME_MacroValues['gzDebug'])
      logger = fmeobjects.FMELogFile()
      gzfme.logger = logger
Shutdown Python:
      import fmeobjects, gzfme

      gzfme.shutdown(Errors,str(FME_MacroValues['IgnoreErrors']),FME_TotalFeaturesWritten,FME_MacroValues)

      del Errors
      del logger
      del ErrorUniqueID
      del ErrorRequiredValue
      del ErrorValueMap
      del debug
      gzfme.logger = None

Parameters:
- DestDataset_GEODATABASE_SDE = sde   # Destination Esri ArcSDE Geodatabase Dataset
- OUT_CONNECTION_FILE_GEODATABASE_SDE = C:\Apps\Gizinta\gseUW\ETL\serverConfig\GIS Staging.sde   # Connection File
- ProductionConnectionFile = C:\Apps\Gizinta\gseUW\ETL\serverConfig\GIS Production.sde   # SDE Connection File |*.sde Production Connection File
- GizintaProject = C:\Apps\Gizinta\gseUW\ETL\config\fpLoadPlaylist.xml   # Select the Gizinta Xml File to use
- TargetFieldQA = True   # Choose whether to perform QA on Target Fields
- SourceFieldQA = False   # Choose whether to perform QA on Source Fields
- IgnoreErrors = False   # Ignore Errors and continue
- SourceDatasetTypes = CADDataset   # Enter the Gizinta Source Dataset Type
- SourceCoordinateSystem = EPSG:2285   # Source Coordinate System
- gzDebug = False   # Enable gzDebug (True/False)
- LOG_FILE =   # Log File
- FEATURE_TYPES = Floor_Poly FloorArea_Isometric FloorplanLine FloorplanLine_Isometric InteriorSpace InteriorSpace_Isometric InteriorSpace_Point FloorArea   # Feature Types to Write
- FEATURE_TYPES_READ = BSE RMS GSF   # Feature Types to Read
- SourceDataset_ESRIMSD = C:\Vault_Mirror\CADVault\UWS-UW Seattle\**\*XP*.dwg   # Source Autodesk AutoCAD DWG/DXF File(s)
- truncate = N   # Truncate before load option
- FEATURE_TYPES_PROD = Floor FloorPageTemplate
- elevName = schelev   # Floor Elevation Value Name

Readers:
- GEODATABASE_SDE_1: GEODATABASE_SDE from $(DestDataset_GEODATABASE_SDE)
- ESRIMSD_1: ESRIMSD from $(SourceDataset_ESRIMSD)
- GEODATABASE_SDE_2: GEODATABASE_SDE

Writers:
- GEODATABASE_SDE_3: GEODATABASE_SDE to $(DestDataset_GEODATABASE_SDE)

BSE (reader ESRIMSD_1)
    attributes: FACFLOOR char(254), FACNUM char(254), FLOOR char(254)
    -> Tester
Tester
    TEST_MODE = Automatic
    TEST_CLAUSE = TEST $(FEATURE_TYPES_READ) CONTAINS @Value(fme_feature_type)
    BOOL_OP = OR
    TEST_DESCRIPTION = ""
    PASSED -> AttributeExposer
AttributeExposer
    ATTR_LIST = fme_basename
    -> AttributeCopier
AttributeCopier
    ATTR_LIST = DRAWING,fme_basename
    -> gzFieldCalculator [AddFieldsValues_Input_1]
gzFieldCalculator
    AddFieldsValues_Output_1 -> AttributeExposer_2
AttributeExposer_2
    ATTR_LIST = FLOORID,autocad_layer,SPACEID
    -> BulkAttributeRenamer_2
BulkAttributeRenamer_2
    PATTERN_ACTION_DISP = Change Case
    ATTRCHOICE = All Attributes
    CASE_CHANGE_TYPE = lowercase
    -> EsriReprojector
    -> TestFilter_3
TestFilter_3
    TEST_LIST = BOOL_OP,OR,COMPOSITE_TEST,<Unused>,TEST_CLAUSE,"TEST @Value(fme_feature_type) = Floor_Poly",Floor_Poly,BOOL_OP,OR,COMPOSITE_TEST,<Unused>,TEST_CLAUSE,"TEST @Value(fme_feature_type) = FloorplanLine",FloorplanLine,BOOL_OP,OR,COMPOSITE_TEST,<Unused>,TEST_CLAUSE,"TEST @Value(fme_feature_type) = InteriorSpace",InteriorSpace
    DEFAULT_VALUE = <UNFILTERED>
    Floor_Poly -> AttributeExposer_3
Note: removing calc for area. donut builder will not calc correct area / ac 3-2-20
AttributeExposer_3
    ATTR_LIST = floorid
    -> DonutBuilder_2
Note: added donut builder to account for GSF donuts and calculate correct area / ac 2-19-19
DonutBuilder_2
    ALLOW_CYCLES = No
    DROP = yes
    CONNECT_Z_MODE = First Wins
    AREA -> Aggregator_2
Note: get native CAD area for GSF
Aggregator_2
    ORDERED = No
    GROUP_BY = floorid
    MODE = Assemble One Level
    SEP = ,
    AGGREGATE_TYPE = Homogeneous Collection (If Possible)
    ACCUM_ATTRS_NAME = Yes
    AGGREGATE -> AreaCalculator_2
AreaCalculator_2
    AREA_ATTR = _area
    AREA_TYPE = Plane Area
    MULT = 1
    -> FeatureMerger_3 [SUPPLIER]
EsriReprojector
    GEOTRANSFORMATION_DIRECTION = Forward
    INTERPOLATION_TYPE_NAME = Nearest Neighbor
    SOURCE = $(SourceCoordinateSystem)
    RASTER_CELL_SIZE = Preserve Cells
    DEST = ESRIWKT|WGS_1984_Web_Mercator_Auxiliary_Sphere|PROJCS["WGS_1984_Web_Mercator_Auxiliary_Sphere",GEOGCS["GCS_WGS_1984",DATUM["D_WGS_1984",SPHEROID["WGS_1984",6378137.0,298.257223563]],PRIMEM["Greenwich",0.0],UNIT["Degree",0.0174532925199433]],PROJECTION["Mercator_Auxiliary_Sphere"],PARAMETER["False_Easting",0.0],PARAMETER["False_Northing",0.0],PARAMETER["Central_Meridian",0.0],PARAMETER["Standard_Parallel_1",0.0],PARAMETER["Auxiliary_Sphere_Type",0.0],UNIT["Meter",1.0]]
    REPROJECTED -> ArcSDEGridSnapper
ArcSDEGridSnapper
    PRECISION_DISPLAY = High precision (53 bit)
    ZSCALE = 10000
    SCALE = 10000
    XMIN = -20037700
    ZMIN = -100000
    YMIN = -30241100
    OUTPUT_INT = No
    SNAPPED -> TestFilter
TestFilter
    TEST_LIST = BOOL_OP,OR,COMPOSITE_TEST,<Unused>,TEST_CLAUSE,"TEST @Value(fme_feature_type) = Floor_Poly",Floor_Poly,BOOL_OP,OR,COMPOSITE_TEST,<Unused>,TEST_CLAUSE,"TEST @Value(fme_feature_type) = FloorplanLine",FloorplanLine,BOOL_OP,OR,COMPOSITE_TEST,<Unused>,TEST_CLAUSE,"TEST @Value(fme_feature_type) = InteriorSpace",InteriorSpace
    DEFAULT_VALUE = <UNFILTERED>
    Floor_Poly -> gzFixCatwalksFloors
    FloorplanLine -> gzAggregateLines [Aggregator_Input]
    InteriorSpace -> gzFixCatwalksSpaces
Note: Aggregate FloorplanLines by Floor and autocad_layer
Note: Get rid of catwalks for Floor_Polys
gzFixCatwalksFloors
    Tolerance = 0.001
    Feature_Type = Floor_Poly
    UniqueID = @Value(floorid)
    -> FeatureMerger [REQUESTOR]
gzAggregateLines: gzAggregateFloorplanLines
    FLOORID = @Value(floorid)
    Aggregator_Aggregate -> FeatureMerger [REQUESTOR]
Note: Get rid of catwalks for interior spaces
gzFixCatwalksSpaces
    Tolerance = 0.001
    Feature_Type = InteriorSpace
    UniqueID = @Value(spaceid)
    -> FeatureMerger [REQUESTOR]
FloorPageTemplate (reader GEODATABASE_SDE_2)
    attributes: OBJECTID integer, SITEID char(60), BUILDINGID char(60), CALCROT double, LOCALROT double, SOURCEID char(30), SOURCEDWG char(60), LASTUPDATE date, LASTEDITOR char(30), SHAPE.STArea() double, SHAPE.STLength() double, SCHELEV integer, FLOORLEVEL integer, GROUNDELEV double, FLOORAREA char(3), StackLevel double, DDPFLOORSORT char(71), FLOORCODE char(20), INTERIORSPACE char(3), BLDGNAME char(30), DRAWINGNAME char(100), NAMELONG char(100), SENSITIVITY char(30), FLOORID char(60), NAMESHORT char(50), FLOORPLANLINE char(3)
    -> AttributeExposer_5
Note: Building and Floor Data
AttributeExposer_5
    ATTR_LIST = fme_feature_type,BUILDINGID,FLOORID
    -> BulkAttributeRenamer_4
BulkAttributeRenamer_4
    PATTERN_ACTION_DISP = Change Case
    ATTRCHOICE = All Attributes
    CASE_CHANGE_TYPE = lowercase
    -> gseGetBldgFloorInfo [TestFilter_2_Input]
gseGetBldgFloorInfo
    flr = @Value(floorid)
    FeatureMerger_3_Merged -> FeatureMerger [SUPPLIER]
FeatureMerger
    ATTR_CONFLICT_RES = Use Requestor
    IGNORE_NULLS = No
    MERGE_TYPE = Attributes Only
    JOIN_KEYS = @Value(floorid) @Value(floorid) AUTO
    ATTR_ACCUM_MODE = Merge Supplier
    SUPPLIERS_FIRST = No
    PROCESS_DUPS = No
    MERGED -> TestFilter_2
    NOT_MERGED -> FeatureMerger_NotMerged
TestFilter_2
    TEST_LIST = BOOL_OP,OR,COMPOSITE_TEST,<Unused>,TEST_CLAUSE,"TEST @Value(fme_feature_type) = Floor_Poly",Floor_Poly,BOOL_OP,OR,COMPOSITE_TEST,<Unused>,TEST_CLAUSE,"TEST @Value(fme_feature_type) = FloorplanLine",FloorplanLine,BOOL_OP,OR,COMPOSITE_TEST,<Unused>,TEST_CLAUSE,"TEST @Value(fme_feature_type) = InteriorSpace",InteriorSpace
    DEFAULT_VALUE = <UNFILTERED>
    Floor_Poly -> AttributeRemover
    Floor_Poly -> 3DForcer
    FloorplanLine -> 3DForcer
    FloorplanLine -> gzTiltLines
    InteriorSpace -> InsidePointReplacer
    InteriorSpace -> gzTiltRooms
    InteriorSpace -> 3DForcer
AttributeRemover
    REMOVE_ATTRS = floorarea
    -> DonutBuilder_3
Note: merge to get elevation value for floor
DonutBuilder_3
    ALLOW_CYCLES = No
    DROP = yes
    CONNECT_Z_MODE = First Wins
    AREA -> Aggregator
Aggregator
    ORDERED = No
    GROUP_BY = floorid
    MODE = Assemble One Level
    SEP = ,
    AGGREGATE_TYPE = Homogeneous Collection (If Possible)
    ACCUM_ATTRS_NAME = Yes
    AGGREGATE -> FeatureMerger_3 [REQUESTOR]
FeatureMerger_3
    ATTR_CONFLICT_RES = Use Requestor
    IGNORE_NULLS = No
    MERGE_TYPE = Attributes Only
    JOIN_KEYS = @Value(fme_feature_type) @Value(fme_feature_type) AUTO @Value(floorid) @Value(floorid) AUTO
    REJECT_NULL_MISSING_KEYS = No
    ATTR_ACCUM_MODE = Merge Supplier
    SUPPLIERS_FIRST = No
    PROCESS_DUPS = No
    MERGED -> AttributeCreator_2
    NOT_MERGED -> AttributeCreator_2
Note: added donut builder to account for GSF donuts and calculate correct area / ac 2-19-19
AttributeCreator_2
    ATTR_TABLE = SET_TO floorarea = @Value(_area)
    -> FloorArea
FloorArea: AttributeCreator
    ATTR_LIST = fme_feature_type,FloorArea
    -> gzTiltLines_2
    -> 3DForcer
    -> FloorArea_Output
FloorArea_Output: Inspector
gzTiltLines_2: gzTiltRooms [off]
    CALCROT = @Value(calcrot)
    MARGIN = .1
    _XMAX = @Value(_xmax)
    _YMIN = @Value(_ymin)
    pBUILDINGID = @Value(buildingid)
    pFLOORID = @Value(floorid)
    STACKLEVEL = @Value(stacklevel)
    _YMAX = @Value(_ymax)
    _XMIN = @Value(_xmin)
    SPACING = 1
    tiltDemoninator = 2
    SPACEID = @Value(spaceid)
    -> _Isometric
gzTiltLines: gzTiltRooms [off]
    CALCROT = @Value(calcrot)
    MARGIN = .1
    _XMAX = @Value(_xmax)
    _YMIN = @Value(_ymin)
    pBUILDINGID = @Value(buildingid)
    pFLOORID = @Value(floorid)
    STACKLEVEL = @Value(stacklevel)
    _YMAX = @Value(_ymax)
    _XMIN = @Value(_xmin)
    SPACING = 1
    tiltDemoninator = 2
    SPACEID = @Value(spaceid)
    -> _Isometric
gzTiltRooms [off]
    CALCROT = @Value(calcrot)
    MARGIN = .1
    _XMAX = @Value(_xmax)
    _YMIN = @Value(_ymin)
    pBUILDINGID = @Value(buildingid)
    pFLOORID = @Value(floorid)
    STACKLEVEL = @Value(stacklevel)
    _YMAX = @Value(_ymax)
    _XMIN = @Value(_xmin)
    SPACING = 1
    tiltDemoninator = 2
    SPACEID = @Value(spaceid)
    -> _Isometric
_Isometric: AttributeCreator
    ATTR_LIST = fme_feature_type,@Value(fme_feature_type)_Isometric
    -> 3DForcer
InsidePointReplacer
    INSIDEPOINT -> InteriorSpace_Point
Note: disabled tilts / ac 2-19-19
InteriorSpace_Point: AttributeCreator
    ATTR_LIST = fme_feature_type,InteriorSpace_Point
    -> 3DForcer
3DForcer
    KEEPZVAL = No
    ZVALATTR = @Value($(elevName)) * 0.3048
    -> BulkAttributeRenamer_3
BulkAttributeRenamer_3
    PATTERN_ACTION_DISP = Change Case
    ATTRCHOICE = All Attributes
    CASE_CHANGE_TYPE = UPPERCASE
    -> gzSourceTargetQA [SourceTargetQA_Input_1]
gzSourceTargetQA
    SourceTargetQA_Output_1 -> gzWriteData [gzFeatures]
gzWriteData
    HASERRORS = @Value(HasErrors)
    GroupBy = @Value(FLOORID)
    IgnoreErrors = False
    gzLogWriter -> gzLog (writer GEODATABASE_SDE_3)
    gzFeatureWriter -> TruncateFirst
    gzErrorWriter -> gzError (writer GEODATABASE_SDE_3)
gzLog (writer GEODATABASE_SDE_3)
    attributes: procname char(255), loadtime date, loadname char(255), dataset char(255), completed smallint, loaduser char(255), activeflag char(255)
TruncateFirst: TestFilter
    TEST_LIST = BOOL_OP,OR,COMPOSITE_TEST,<Unused>,TEST_CLAUSE,"TEST $(truncate) = Y",Y,BOOL_OP,OR,COMPOSITE_TEST,<Unused>,TEST_CLAUSE,"TEST $(truncate) = N",N
    DEFAULT_VALUE = <UNFILTERED>
    Y -> Features (writer GEODATABASE_SDE_3)
    N -> Features00 (writer GEODATABASE_SDE_3)
Features (writer GEODATABASE_SDE_3)
Features00 (writer GEODATABASE_SDE_3)
gzError (writer GEODATABASE_SDE_3)
    attributes: procname char(255), sourcename char(255), srcidfield char(255), srcidval char(255), dataset char(255), reason char(255), erruser char(255), errtime date, activeflag char(255)
FeatureMerger_NotMerged: Logger
    MAXCOORDS = 20
    MESSAGE = Serious error - Missing Bldg/Floor ID for:
    MAXFEATS = 200

FME custom transformer SelfIntersectChecker
Separates self-intersecting features from the rest of input. This custom transformer does not change the geometry of self-intersecting features. If you want to remove self-intersections, try the " SelfIntersector " transformer.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Input (input)
    -> PartCounter
PartCounter
    COUNT_ATTR = _part_count1
    RECURSIVE_PARAM = No
    -> COUNTER
COUNTER: Counter
    START = 0
    SCOPE = Local
    DOMAIN = counter
    CNT_ATTR = _selfID
    -> GeometryExtractor
GeometryExtractor
    OGCVERSION = 1.2
    ATTR = _geometry
    KIND_LONG = OGC Well Known Text
    -> SelfIntersector
SelfIntersector
    SEG_ATTR = _segments
    SELF_INTERSECTED -> DuplicateRemover
DuplicateRemover
    KEYATTR = _selfID
    UNIQUE -> TESTER
TESTER: Tester
    TEST_MODE = NUMERIC
    TEST_LIST = &_segments,>,1
    TEST_CLAUSE = TEST @Value(_segments) > 1
    BOOL_OP = OR
    PASSED -> GeometryReplacer
    FAILED -> PartCounter_2
PartCounter_2
    COUNT_ATTR = _part_count2
    RECURSIVE_PARAM = No
    -> TESTER_2
TESTER_2: Tester
    TEST_MODE = Automatic
    TEST_LIST = &_part_count1,=,&_part_count2
    TEST_CLAUSE = TEST @Value(_part_count1) = @Value(_part_count2)
    BOOL_OP = OR
    PASSED -> ATTRIBUTEREMOVER
    FAILED -> GeometryReplacer
ATTRIBUTEREMOVER: AttributeRemover
    REMOVE_ATTRS = _selfID,_geometry,_segments
    -> NotSelfIntersecting (output)
NotSelfIntersecting (output)
GeometryReplacer
    ATTR = _geometry
    KIND_LONG = OGC Well Known Text
    -> ATTRIBUTEREMOVER_2
ATTRIBUTEREMOVER_2: AttributeRemover
    REMOVE_ATTRS = _selfID,_geometry,_segments
    -> SelfIntersecting (output)
SelfIntersecting (output)

FME custom transformer gzAggregateFloorplanLines
Aggregate lines by floor and fme_feature_type

Parameters:
- FLOORID = @Value(FLOORID)

Aggregator_Input (input)
    -> AttributeExposer
AttributeExposer
    ATTR_LIST = autocad_layer,floorid
    -> Chopper
Chopper
    MODE = By Vertex
    CHOPPED_ATTR = _chopped
    MAX_VERTICES = 2
    REMNANT_ATTR = _remnant
    -> GeometryFilter_2
GeometryFilter_2
    BREAK_AGG = No
    LINE -> SelfIntersector_2
    ARC -> SelfIntersector_2
SelfIntersector_2
    SEG_ATTR = _segments
    SELF_INTERSECTED -> GeometryCoercer_3
GeometryCoercer_3
    KIND = fme_line
    COERCED -> LengthCalculator_3
LengthCalculator_3
    DIM = 2
    MULT = 1
    LEN_ATTR = _length
    -> Tester_2
Tester_2
    TEST_MODE = Automatic
    TEST_CLAUSE = TEST @Value(_length) > .01
    BOOL_OP = OR
    TEST_DESCRIPTION = ""
    PASSED -> Aggregator_2
Aggregator_2
    ORDERED = No
    GROUP_BY = autocad_layer FLOORID
    CONTAIN_INDIVID_GEOMS = No
    SEP = ,
    ACCUM_ATTRS_NAME = Yes
    AGGREGATE -> Aggregator_Aggregate (output)
Aggregator_Aggregate (output)

FME custom transformer gzTiltRooms
Tilt Rooms in floorplans to create a pseudo-isometric view of the rooms and floors

Parameters:
- pBUILDINGID = 1327   # Enter the Building Identifier
- pFLOORID = 1327_01   # Enter the FacFloor Number
- _XMAX = @Value(_xmax)   # Xmax
- _YMAX = @Value(_ymax)   # Ymax
- _YMIN = @Value(_ymin)   # Ymin
- tiltDemoninator = 2   # Tilt = 2 will tilt 50% or y/2
- STACKLEVEL = @Value(stacklevel)   # stacklevel
- CALCROT = @Value(calcrot)   # calcrot
- SPACEID = @Value(spaceid)   # spaceid
- _XMIN = @Value(_xmin)   # Xmin
- MARGIN = .1   # margin
- SPACING = 1   # spacing

INPUT (input)
    -> AttributeExposer
Note: Function will rotate flat/horizontal. Add 15 degrees
AttributeExposer
    ATTR_LIST = spacing
    -> Rotation
Rotation: ExpressionEvaluator
    EXPRESSION = @Value(calcrot) + 15
    VAL_ATTR = calculated_rotation
    -> Rotator
Rotator
    XORIG = @Value(_xmax)
    ANGLE = @Value(calculated_rotation)
    YORIG = @Value(_ymax)
    ROTATED -> Y_Base
Note: Add 10 meters to the base of every point * stacklevel + y height
Y_Base: ExpressionEvaluator
    EXPRESSION = (@Value(_ymax)  + 10 ) + (@Value(stacklevel)  * $(SPACING) * (@abs(@Value(_ymax) - @Value(_ymin))/$(tiltDemoninator)))
    VAL_ATTR = _yBase
    -> tiltFactor
tiltFactor: ExpressionEvaluator
    EXPRESSION = "$(SPACING) * $(tiltDemoninator)\n\n"
    VAL_ATTR = _tiltFactor
    -> AttributeCreator
AttributeCreator
    ATTR_LIST = _subtracty,@Value(_ymax),_margin,$(MARGIN)
    -> TiltFeatures
TiltFeatures: PythonCaller
    PYTHONSYMBOL = FeatureProcessor
    PYTHONSOURCE:
      import fmeobjects

      debug = False
      # Template Function interface:
      def processFeature(feature):
          pass

      # Template Class Interface:
      class FeatureProcessor(object):
          def __init__(self):
              pass
          def input(self,feature):
              ### Formula is yBase + ((y - subtracty) / tiltFactor) * (1 - margin)
              yBase = float(feature.getAttribute("_yBase"))
              subtracty = float(feature.getAttribute("_subtracty"))
              tiltFactor = float(feature.getAttribute("_tiltFactor"))
              margin = float(feature.getAttribute("_margin"))
              heightPercent = 1 - margin
              if debug == True:
                  logger.logMessageString(str(yBase) + '|' + str(subtracty) + '|' +  str(tiltFactor) + '|' +  str(margin))
              parts = feature.getDonutParts()
              for part in parts:
                  coords = part.getAllCoordinates()
                  for i in xrange(len(coords)):
                      # Assume 2D geometries here
                      y = coords[i][1]
                      yDiff = y - subtracty
                      rawY = yDiff / tiltFactor
                      addY = rawY * heightPercent
                      tilt_y = yBase + addY
                      coords[i] = (coords[i][0], tilt_y)

                      if debug == True:
                          logger.logMessageString("y="+str(y))
                          logger.logMessageString("yBase="+str(yBase))
                          logger.logMessageString("rawY="+str(rawY))
                          #logger.logMessageString("yDiff="+str(yDiff))
                          #logger.logMessageString("heightPercent="+str(heightPercent))
                          #logger.logMessageString("tiltFactor="+str(tiltFactor))
                          logger.logMessageString("addY="+str(addY))
                          logger.logMessageString("tilt_y="+str(tilt_y))
                  part.resetCoords()
                  part.addCoordinates(coords)
              if len(parts) > 0:
                  feature.makeDonuts(parts)
                  del coords, parts
              self.pyoutput(feature)

          def close(self):
              pass
    NEW_ATTRIBUTES = _subtracty _yBase margin _tiltFactor
    -> GeometryValidator_3
GeometryValidator_3
    PRESETS = Custom
    SELF_INTERSECTING = SELF_INTERSECTING
    PLANAR_SURFACE = PLANAR_SURFACE
    ARC_ENDPOINT_TOLERANCE_MODE = Custom
    ARC_ENDPOINT_TOLERANCE = 0.001
    DUP_COORDS_CHECK_Z = Yes
    REPAIR = No
    CHECK_HOLE_TOUCHING_POLYGON = Yes
    PLANAR_TOLERANCE = 0.001
    CONSECUTIVE_IDENTICAL_VERTICES_2D = CONSECUTIVE_IDENTICAL_VERTICES_2D
    PLANAR_TOLERANCE_MODE = Custom
    ISSUE_ATTR_NAME = _issues
    TYPE_REPAIR = TYPE_REPAIR
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    PASSED -> OUTPUT (output)
    FAILED -> Generalizer
Generalizer
    ALG_TEXT = Douglas (Generalize)
    PRESERVE = No
    TOLERANCE = .05
    -> SpikeRemover
SpikeRemover
    SPIKEANGLE = 3
    UNCHANGED -> GeometryValidator_2
    CHANGED -> GeometryValidator_2
GeometryValidator_2
    PRESETS = Custom
    SELF_INTERSECTING = SELF_INTERSECTING
    DUP_COORDS_CHECK_Z = No
    REPAIR = Yes
    CHECK_HOLE_TOUCHING_POLYGON = Yes
    CONSECUTIVE_IDENTICAL_VERTICES_2D = CONSECUTIVE_IDENTICAL_VERTICES_2D
    ISSUE_ATTR_NAME = _issues
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    PASSED -> OUTPUT (output)
    FAILED -> GeometryValidator_2_Failed
    REPAIRED -> OUTPUT (output)
OUTPUT (output)
GeometryValidator_2_Failed: Logger
    MAXCOORDS = 20
    MESSAGE = Feature is:
    MAXFEATS = 20

FME custom transformer gzBuildingAngle

Parameters:
- BUILDINGID =   # Enter the Building ID

INPUT (input)
    -> Chopper_2
    -> FeatureMerger_3 [REQUESTOR]
Chopper_2
    MAX = 2
    CHOPPED -> LengthCalculator_2
LengthCalculator_2
    DIM = 2
    MULT = 1
    LEN_ATTR = _length
    -> StatisticsCalculator_2
StatisticsCalculator_2
    COUNT_ATTR = _count
    NUMERIC_ATTR = _numeric_count
    PASS_THROUGH = Yes
    MAX_ATTR = _max
    RANGE_ATTR = _range
    MEDIAN_ATTR = _median
    STATS_ATTR = _length
    SUM_ATTR = _sum
    MEAN_ATTR = _mean
    MIN_ATTR = _min
    MODE_ATTR = _mode
    STDEV_ATTR = _stdev
    STATISTICS -> TestFilter_6
TestFilter_6
    TEST_LIST = BOOL_OP,OR,COMPOSITE_TEST,<Unused>,TEST_CLAUSE,"TEST ""@Value(_length)"" = ""@Value(_max)""",_length = _max
    DEFAULT_VALUE = <UNFILTERED>
    _length = _max -> CoordinateExtractor_4
CoordinateExtractor_4
    Z_DEFAULT = -9999
    Y_ATTR = _y1
    Z_ATTR = _z
    IND = 0
    X_ATTR = _x1
    -> CoordinateExtractor_6
CoordinateExtractor_6
    Z_DEFAULT = -9999
    Y_ATTR = _y2
    Z_ATTR = _z
    IND = 1
    X_ATTR = _x2
    -> TestFilter_4
TestFilter_4
    TEST_LIST = BOOL_OP,OR,COMPOSITE_TEST,<Unused>,TEST_CLAUSE,"TEST ""@Value(_y2)"" >= ""@Value(_y1)""",_y2 >= _y1
    DEFAULT_VALUE = <UNFILTERED>
    _y2 >= _y1 -> ExpressionEvaluator_7
    <UNFILTERED> -> ExpressionEvaluator_4
Note: Calculate angle of the longest side
ExpressionEvaluator_7
    EXPRESSION = @atan2(@Value(_x1)-@Value(_x2),@Value(_y1)-@Value(_y2))*180.0/(22/7.0)
    VAL_ATTR = _angle
    -> ExpressionEvaluator_8
ExpressionEvaluator_4
    EXPRESSION = @atan2(@Value(_x2)-@Value(_x1),@Value(_y2)-@Value(_y1))*180.0/(22/7.0)
    VAL_ATTR = _angle
    -> ExpressionEvaluator_8
ExpressionEvaluator_8
    EXPRESSION = @Value(_angle) + 90.0
    VAL_ATTR = _angle
    -> TestFilter_5
TestFilter_5
    TEST_LIST = BOOL_OP,OR,COMPOSITE_TEST,<Unused>,TEST_CLAUSE,"TEST ""@Value(_angle)"" > ""180.0""",_angle > 180.0
    DEFAULT_VALUE = <UNFILTERED>
    _angle > 180.0 -> ExpressionEvaluator_10
    <UNFILTERED> -> Sorter_2
ExpressionEvaluator_10
    EXPRESSION = @Value(_angle) -180.0
    VAL_ATTR = _angle
    -> Sorter_2
Sorter_2
    SORT_PARM = _length NUMERIC DESCENDING
    SORTED -> FeatureMerger_3 [SUPPLIER]
FeatureMerger_3
    MERGE_TYPE = Attributes Only
    PROCESS_DUPS = No
    BUILD_INCOMPLETE = No
    REFEEATTR = $(BUILDINGID)
    REFERATTR = $(BUILDINGID)
    COMPLETE -> GeometryExtractor_2
GeometryExtractor_2
    ATTR = _geometry
    KIND_LONG = FME Binary
    -> CenterOfGravityReplacer
CenterOfGravityReplacer
    CENTEROFGRAVITY -> CoordinateExtractor_3
CoordinateExtractor_3
    Z_DEFAULT = -9999
    Y_ATTR = YCENTER
    Z_ATTR = _z
    IND = 0
    X_ATTR = XCENTER
    -> GeometryReplacer
GeometryReplacer
    ATTR = _geometry
    KIND_LONG = FME Binary
    -> AttributeCreator
Note: Calculate X and Y Center Point
AttributeCreator
    ATTR_LIST = MODANGLE,0,SPACING,50,MARGIN,.2,HULLROT,@Value(_angle)
    -> OUTPUT (output)
OUTPUT (output)

FME custom transformer gzAggregateLines
Clean geometries and Aggregate Floorplan lines into _Optimized features

INPUT (input)
    -> CoordinateCounter
CoordinateCounter
    CNT_ATTR = _coordcount
    -> LengthCalculator_2
LengthCalculator_2
    DIM = 2
    MULT = 1
    LEN_ATTR = _length
    -> TestFilter_6
TestFilter_6
    TEST_LIST:
      BOOL_OP,AND,COMPOSITE_TEST,<Unused>,TEST_CLAUSE,"TEST ""@Value(_coordcount)"" >= ""2""
      TEST ""@Value(_length)"" >= "".001""",2pts & length > .01
    DEFAULT_VALUE = <UNFILTERED>
    2pts & length > .01 -> SelfIntersectChecker
SelfIntersectChecker
    NotSelfIntersecting -> GeometryCoercer
    SelfIntersecting -> SelfIntersector
SelfIntersector
    SEG_ATTR = _segments
    SELF_INTERSECTED -> GeometryCoercer
GeometryCoercer
    KIND = fme_line
    COERCED -> Aggregator_2
Aggregator_2
    ORDERED = No
    GROUP_BY = FLOORID
    CONTAIN_INDIVID_GEOMS = No
    SEP = ,
    ACCUM_ATTRS_NAME = Yes
    AGGREGATE -> OUTPUT (output)
OUTPUT (output)

FME custom transformer gseGetBldgFloorInfo

Parameters:
- flr =   # Floor ID

TestFilter_2_Input (input)
    -> AttributeExposer
AttributeExposer
    ATTR_LIST = floorid,buildingid,bldg,schelev,fme_feature_type,floor,siteid,calcrot,floor_name,floor_level,stacklevel
    -> BulkAttributeRenamer
BulkAttributeRenamer
    PATTERN_ACTION_DISP = Change Case
    ATTRCHOICE = All Attributes
    CASE_CHANGE_TYPE = lowercase
    -> TestFilter_2
TestFilter_2
    TEST_LIST = BOOL_OP,OR,COMPOSITE_TEST,<Unused>,TEST_CLAUSE,"TEST @Value(fme_feature_type) = Floor",Floor,BOOL_OP,OR,COMPOSITE_TEST,<Unused>,TEST_CLAUSE,"TEST @Value(fme_feature_type) = FloorPageTemplate",FloorPageTemplate
    DEFAULT_VALUE = <UNFILTERED>
    Floor -> FeatureMerger_3 [REQUESTOR]
    FloorPageTemplate -> BoundsExtractor
BoundsExtractor
    YMAX = _ymax
    XMIN = _xmin
    XMAX = _xmax
    ZMIN = _zmin
    YMIN = _ymin
    ZMAX = _zmax
    -> LengthCalculator
LengthCalculator
    DIM = 2
    MULT = 1
    LEN_ATTR = _bldg_outline_length
    -> FeatureMerger_3 [SUPPLIER]
FeatureMerger_3
    MERGE_TYPE = Attributes Only
    PROCESS_DUPS = No
    IGNORE_NULLS = Yes
    SUPPLIERS_FIRST = No
    SUPPLIER_PREFIX_DUMMY = YES
    JOIN_KEYS = @Value(floor) @Value(floor) AUTO
    MERGED -> FeatureMerger_3_Merged (output)
FeatureMerger_3_Merged (output)

FME custom transformer gzFixCatwalks
Fix "catwalks" in source polygons from CAD. Typically for rooms inside of rooms and other inner polygons in CAD there are lines drawn so that room areas can be calculated. This transformer will remove those lines and other small self-intersections.

Parameters:
- Tolerance = 0.001   # Generalization tolerance
- UniqueID = SPACEID   # UniqueID field value for polygons
- Feature_Type = InteriorSpace_All   # Feature Type to process

INPUT (input)
    -> ParameterFetcher
ParameterFetcher
    ATTR_LIST = _UniqueID {$(UniqueID)}
    -> AttributeExposer
AttributeExposer
    ATTR_LIST = fme_feature_type,drawing,buildingid,floorid,spaceid
    -> Tester
Tester
    TEST_MODE = Automatic
    TEST_CLAUSE = TEST @Value(fme_feature_type) = $(Feature_Type)
    BOOL_OP = OR
    TEST_DESCRIPTION = ""
    PASSED -> Generalizer
    FAILED -> OUTPUT (output)
Generalizer
    ALG_TEXT = Douglas (Generalize)
    PRESERVE = No
    TOLERANCE = $(Tolerance)
    -> SelfIntersectChecker
SelfIntersectChecker
    NotSelfIntersecting -> GeometryCoercer_2
    SelfIntersecting -> SelfIntersector
SelfIntersector
    SEG_ATTR = _segments
    SELF_INTERSECTED -> Generalizer_2
Generalizer_2
    ALG_TEXT = Thin (Generalize)
    PRESERVE = No
    TOLERANCE = .05
    -> SpikeRemover
SpikeRemover
    SPIKEANGLE = 2
    UNCHANGED -> DonutBuilder
    CHANGED -> DonutBuilder
DonutBuilder
    GROUP_BY = _UniqueID
    ALLOW_CYCLES = No
    DROP = no
    FLAG_ATTR = _hole_flag
    AREA -> Aggregator
Aggregator
    ORDERED = No
    GROUP_BY = _UniqueID
    MODE = Geometry - Assemble One Level
    SEP = ,
    AGGREGATE_TYPE = Homogeneous Collection (If Possible)
    ACCUM_ATTRS_NAME = Yes
    AGGREGATE -> GeometryFilter
GeometryFilter
    BREAK_AGG = No
    GEOM_PORT_NAMES = Area
    AREA -> PartCounter
PartCounter
    COUNT_ATTR = _part_count
    RECURSIVE_PARAM = Yes
    -> GeometryCoercer_2
GeometryCoercer_2
    KIND = fme_polygon
    CHECKZ = No
    COERCED -> SelfIntersectChecker_2
SelfIntersectChecker_2
    NotSelfIntersecting -> OUTPUT (output)
    SelfIntersecting -> Logger_SelfIntersecting
    SelfIntersecting -> AttributeCreator
AttributeCreator
    ATTR_LIST = ErrorGeometry,True,ErrorGeometryDescription,Self Intersecting - @Value(floorid),HasErrors,True
    -> OUTPUT (output)
OUTPUT (output)
Logger_SelfIntersecting
    MAXCOORDS = 20
    MESSAGE = Feature is self-intersecting:
    MAXFEATS = 100
