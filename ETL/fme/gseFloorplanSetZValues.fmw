FME workspace gseFloorplanSetZValues.fmw
Title: GizintaLoader
Description: First Beta release of Gizinta for FME
Usage: Add the xml file and other parameters
Requirements: test
History: 31/10/2013,support@Gizinta.com,First Draft
Legal terms conditions: This work is licensed under the Creative Commons Attribution-ShareAlike 3.0 Unported License.

Parameters:
- DestDataset_GEODATABASE_SDE = sde   # Destination Esri ArcSDE Geodatabase Dataset
- ProductionConnectionFile = C:\Apps\Gizinta\gseUW\ETL\serverConfig\GIS Production.sde   # Enter the path and name of the Production SDE Database connection file
- GizintaProject = C:\Apps\Gizinta\gseUW\ETL\config\fpPlaylistAll.xml   # Select the Gizinta Xml File to use
- flr = %   # Enter the FloorID or like expression
- LOG_FILE = gseFloorplanSetZValues.log   # Log File
- FEATURE_TYPES = InteriorSpace_Tilt FloorplanLine InteriorSpace Floor_Outline Floor_Point Floor_Poly FloorplanLine_Publish FloorArea InteriorSpace_Point   # Feature Types to Write
- FEATURE_TYPES_READ = DBO.FloorArea DBO.Floor_Poly DBO.FloorplanLine DBO.InteriorSpace DBO.InteriorSpace_Point
- SourceDataset_GEODATABASE_SDE = sde   # Source Esri ArcSDE Geodatabase Dataset
- FEATURE_TYPES_PROD = Floor
- elevName = schelev   # Floor Elevation Value Name

Readers:
- GEODATABASE_SDE_1: GEODATABASE_SDE from $(DestDataset_GEODATABASE_SDE)
- GEODATABASE_SDE_2: GEODATABASE_SDE from $(DestDataset_GEODATABASE_SDE)
- GEODATABASE_SDE_3: GEODATABASE_SDE from $(SourceDataset_GEODATABASE_SDE)

Writers:
- GEODATABASE_SDE_4: GEODATABASE_SDE to $(DestDataset_GEODATABASE_SDE)

DBO.FloorArea (reader GEODATABASE_SDE_2)
    attributes: geodb_oid integer, OBJECTID integer, SITEID char(60), BUILDINGID char(60), FLOOR char(20), FLOORID char(60), FloorArea double, SCHELEV smallint, ALTITUDE smallint, SENSITIVITY char(20), SOURCEDWG char(60), IN_DATE date, LAST_USER char(30), GlobalID char(38), FLOOR_NAME char(60), BLDG_NAME char(60), SHAPE.STArea() double, SHAPE.STLength() double
    -> AttributeExposer_2
AttributeExposer_2
    ATTR_LIST = fme_feature_type,SPACEID,FLOORID,FLOORAREA
    -> TestFeatureTypes
TestFeatureTypes: Tester
    TEST_MODE = Automatic
    TEST_CLAUSE = TEST $(FEATURE_TYPES_READ) CONTAINS @Value(fme_feature_type)
    TEST_DESCRIPTION = ""
    BOOL_OP = OR
    PASSED -> BulkAttributeRenamer_2
BulkAttributeRenamer_2
    CASE_CHANGE_TYPE = lowercase
    ATTRCHOICE = All Attributes
    PATTERN_ACTION_DISP = Change Case
    -> FeatureMerger [input 1]
Building_Outline_Point (reader GEODATABASE_SDE_3)
    attributes: geodb_oid integer, OBJECTID integer, SITEID char(60), BUILDINGID char(60), CALCROT double, NUMFLOORS integer, SOURCEDWG char(60), SCALE_85X11 double, SCALE_11X17 double, SENSITIVITY char(20), IN_DATE date, LAST_USER char(30), GlobalID char(38), ALTITUDE double, SOURCEID char(30), DWG_NAME char(255), FLOOR char(6), INTERIORSPACE char(255), NAME_LONG char(255), BLDGHEIGHT double, FLOOR_LEVEL integer, SCHELEV integer, SHAPE.STLength() double, MARGIN double, FLOORPLANLINE char(255), YCENTER double, SHAPE.STArea() double, XCENTER double, FLOORID char(20), SPACING double,
      NAME_SHORT char(255)
    -> AttributeExposer_3
AttributeExposer_3
    ATTR_LIST = fme_feature_type,BUILDINGID,FLOORID
    -> BulkAttributeRenamer
BulkAttributeRenamer
    CASE_CHANGE_TYPE = lowercase
    ATTRCHOICE = All Attributes
    PATTERN_ACTION_DISP = Change Case
    -> FeatureMerger [input 2]
FeatureMerger
    MERGE_TYPE = Attributes Only
    SUPPLIERS_FIRST = No
    SUPPLIER_PREFIX_DUMMY = YES
    JOIN_KEYS = @Value(floorid) @Value(floorid) AUTO
    PROCESS_DUPS = No
    IGNORE_NULLS = Yes
    NOT_MERGED -> FeatureMerger_NotMerged_2
    MERGED -> 3DForcer
3DForcer
    ZVALATTR = @Value($(elevName)) * 0.3048
    -> BulkAttributeRenamer_3
Note: SQL Server/Oracle
BulkAttributeRenamer_3
    CASE_CHANGE_TYPE = UPPERCASE
    ATTRCHOICE = All Attributes
    PATTERN_ACTION_DISP = Change Case
    -> NewFeatureType (writer GEODATABASE_SDE_4)
NewFeatureType (writer GEODATABASE_SDE_4)
FeatureMerger_NotMerged_2: Logger
    MESSAGE = Feature is missing floor data:
    MAXCOORDS = 20
    MAXFEATS = 20000

FME custom transformer gzSetupExtract

INPUT (input)
    -> AttributeExposer
AttributeExposer
    ATTR_LIST = fme_feature_type_name
    -> PythonCaller
PythonCaller
    NEW_ATTRIBUTES = WhereClause *
    PYTHONSOURCE:
      import fmeobjects


      # Template Function interface:
      def processFeature(feature):
          pass

      # Template Class Interface:
      class FeatureProcessor(object):
          def __init__(self):
              pass
          def input(self,feature):
              whereClause = ""
              featType = feature.getAttribute("fme_feature_type_name")
              for sourceDataset in sourceDatasets:
                  sourceName = sourceDataset.getAttributeNode("sourceName").nodeValue
                  if debug == True:
                      logger.logMessageString("gz sources=" + featType + "|" + sourceName)
                  if sourceName == featType:
                      whereClause = getWhereClause(featType)
                      if debug == True:
                          logger.logMessageString("gz Where=" + whereClause)
                      feature.setAttribute("WhereClause",whereClause)
                      self.pyoutput(feature)

          def close(self):
              pass
    PYTHONSYMBOL = FeatureProcessor
    -> OUTPUT (output)
OUTPUT (output)

FME custom transformer gzBuildingAngle

Parameters:
- BUILDINGID =   # Enter the Building ID

INPUT (input)
    -> Chopper_2
    -> FeatureMerger_3 [input 1]
Chopper_2
    MAX = 2
    CHOPPED -> LengthCalculator_2
LengthCalculator_2
    DIM = 2
    MULT = 1
    LEN_ATTR = _length
    -> StatisticsCalculator_2
StatisticsCalculator_2
    MIN_ATTR = _min
    MAX_ATTR = _max
    COUNT_ATTR = _count
    MEAN_ATTR = _mean
    MODE_ATTR = _mode
    STATS_ATTR = _length
    STDEV_ATTR = _stdev
    SUM_ATTR = _sum
    PASS_THROUGH = Yes
    MEDIAN_ATTR = _median
    NUMERIC_ATTR = _numeric_count
    RANGE_ATTR = _range
    STATISTICS -> TestFilter_6
TestFilter_6
    TEST_LIST = BOOL_OP,OR,COMPOSITE_TEST,<Unused>,TEST_CLAUSE,"TEST ""@Value(_length)"" = ""@Value(_max)""",_length = _max
    DEFAULT_VALUE = <UNFILTERED>
    _length = _max -> CoordinateExtractor_4
CoordinateExtractor_4
    Y_ATTR = _y1
    Z_DEFAULT = -9999
    X_ATTR = _x1
    IND = 0
    Z_ATTR = _z
    -> CoordinateExtractor_6
CoordinateExtractor_6
    Y_ATTR = _y2
    Z_DEFAULT = -9999
    X_ATTR = _x2
    IND = 1
    Z_ATTR = _z
    -> TestFilter_4
TestFilter_4
    TEST_LIST = BOOL_OP,OR,COMPOSITE_TEST,<Unused>,TEST_CLAUSE,"TEST ""@Value(_y2)"" >= ""@Value(_y1)""",_y2 >= _y1
    DEFAULT_VALUE = <UNFILTERED>
    _y2 >= _y1 -> ExpressionEvaluator_7
    <UNFILTERED> -> ExpressionEvaluator_4
Note: Calculate angle of the longest side
ExpressionEvaluator_7
    VAL_ATTR = _angle
    EXPRESSION = @atan2(@Value(_x1)-@Value(_x2),@Value(_y1)-@Value(_y2))*180.0/(22/7.0)
    -> ExpressionEvaluator_8
ExpressionEvaluator_4
    VAL_ATTR = _angle
    EXPRESSION = @atan2(@Value(_x2)-@Value(_x1),@Value(_y2)-@Value(_y1))*180.0/(22/7.0)
    -> ExpressionEvaluator_8
ExpressionEvaluator_8
    VAL_ATTR = _angle
    EXPRESSION = @Value(_angle) + 90.0
    -> TestFilter_5
TestFilter_5
    TEST_LIST = BOOL_OP,OR,COMPOSITE_TEST,<Unused>,TEST_CLAUSE,"TEST ""@Value(_angle)"" > ""180.0""",_angle > 180.0
    DEFAULT_VALUE = <UNFILTERED>
    _angle > 180.0 -> ExpressionEvaluator_10
    <UNFILTERED> -> Sorter_2
ExpressionEvaluator_10
    VAL_ATTR = _angle
    EXPRESSION = @Value(_angle) -180.0
    -> Sorter_2
Sorter_2
    SORT_PARM = _length NUMERIC DESCENDING
    SORTED -> FeatureMerger_3 [input 2]
FeatureMerger_3
    MERGE_TYPE = Attributes Only
    BUILD_INCOMPLETE = No
    REFERATTR = $(BUILDINGID)
    REFEEATTR = $(BUILDINGID)
    PROCESS_DUPS = No
    COMPLETE -> GeometryExtractor_2
GeometryExtractor_2
    KIND_LONG = FME Binary
    ATTR = _geometry
    -> CenterOfGravityReplacer
CenterOfGravityReplacer
    CENTEROFGRAVITY -> CoordinateExtractor_3
CoordinateExtractor_3
    Y_ATTR = YCENTER
    Z_DEFAULT = -9999
    X_ATTR = XCENTER
    IND = 0
    Z_ATTR = _z
    -> GeometryReplacer
GeometryReplacer
    KIND_LONG = FME Binary
    ATTR = _geometry
    -> AttributeCreator
Note: Calculate X and Y Center Point
AttributeCreator
    ATTR_LIST = MODANGLE,0,SPACING,50,MARGIN,.2,HULLROT,@Value(_angle)
    -> OUTPUT (output)
OUTPUT (output)
