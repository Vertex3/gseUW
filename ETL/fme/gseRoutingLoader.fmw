FME workspace gseRoutingLoader.fmw
Title: GizintaLoader
Description: First Beta release of Gizinta for FME
Usage: Add the xml file and other parameters
Requirements: test
History: 31/10/2013,support@Gizinta.com,First Draft
Legal terms conditions: This work is licensed under the Creative Commons Attribution-ShareAlike 3.0 Unported License.
Startup Python:
      import xml.dom.minidom
      import os
      import sys
      import time
      import fmeobjects

      ospath = FME_MacroValues['FME_MF_DIR']
      print ospath
      if ospath not in sys.path:
          sys.path.append(ospath)
      import gzfme

      ErrorUniqueID = "ErrorUniqueID"
      ErrorRequiredValue = "ErrorRequiredValue"
      ErrorValueMap = "ErrorValueMap"
      Errors = False

      debug = gzfme.setDebug(FME_MacroValues['gzDebug'])
      logger = fmeobjects.FMELogFile()
      gzfme.logger = logger
Shutdown Python:
      import fmeobjects, gzfme

      gzfme.shutdown(Errors,str(FME_MacroValues['IgnoreErrors']),FME_TotalFeaturesWritten,FME_MacroValues)

      del Errors
      del logger
      del ErrorUniqueID
      del ErrorRequiredValue
      del ErrorValueMap
      del debug
      gzfme.logger = None

Parameters:
- DestDataset_GEODATABASE_SDE = sde   # Destination Esri ArcSDE Geodatabase Dataset
- OUT_CONNECTION_FILE_GEODATABASE_SDE = C:\apps\Gizinta\gseUW\ETL\serverConfig\GIS Production.sde   # Connection File
- ProductionConnectionFile = C:\Apps\Gizinta\gseUW\ETL\serverConfig\GIS Production.sde   # SDE Connection File |*.sde Production Connection File
- GizintaProject = C:\Apps\Gizinta\gseUW\ETL\config\rtLoadPlaylist.xml   # Select the Gizinta Xml File to use
- TargetFieldQA = True   # Choose whether to perform QA on Target Fields
- SourceFieldQA = False   # Choose whether to perform QA on Source Fields
- IgnoreErrors = False   # Ignore Errors and continue
- SourceDatasetTypes = CADDataset GDBDataset   # Enter the Gizinta Source Dataset Type
- SourceCoordinateSystem = EPSG:2285   # Source Coordinate System
- gzDebug = False   # Enable gzDebug (True/False)
- LOG_FILE = gseRoutingLoader.log   # Log File
- FEATURE_TYPES = RT_LineTransition RT_LineRmConnector RT_RoomPoint RT_LineInterior RT_Waypoint RT_Stop RT_DoorPoint RT_Turn   # Feature Types to Write
- FEATURE_TYPES_READ = RT-DOOR-1.0 RT-DOOR-1.5 RT-LINE-1.0 RT-LINE-1.5 RT-STOP-1.0 RT-STOP-1.5 RT-TRANS-1.0-1.5 RT-TRANS-1.5-2.0 RT-TRANS-1.0-2.0   # Feature Types to Read
- SourceDataset_ESRIMSD = C:\Vault_Mirror\CADVault\UWS-UW Seattle\**\*RT*.dwg   # Source Autodesk AutoCAD DWG/DXF File(s)
- truncate = Y   # Truncate before load option
- SourceDataset_GEODATABASE_SDE = sde   # Source Esri ArcSDE Geodatabase Dataset
- FEATURE_TYPES_PROD = Floor
- flr = _   # floorid or wildcard
- elevName = schelev   # name of elevation attribute used for processing

Readers:
- GEODATABASE_SDE_1: GEODATABASE_SDE from $(DestDataset_GEODATABASE_SDE)
- GEODATABASE_SDE_2: GEODATABASE_SDE from $(DestDataset_GEODATABASE_SDE)
- GEODATABASE_SDE_3: GEODATABASE_SDE from $(SourceDataset_GEODATABASE_SDE)
- ACAD_1: ACAD from $(SourceDataset_ESRIMSD)

Writers:
- GEODATABASE_SDE_4: GEODATABASE_SDE to $(DestDataset_GEODATABASE_SDE)

Note: Need to use GDB InteriorSpaces
InteriorSpace (reader GEODATABASE_SDE_3)
    attributes: geodb_oid integer, OBJECTID integer, SITEID char(60), BUILDINGID char(60), FLOORCODE char(20), FLOORID char(60), ROOMNUMBER char(30), SPACEID char(60), SPACECLASS char(60), SPACEAREA double, SOURCEID char(30), SOURCEDWG char(60), LASTUPDATE date, LASTEDITOR char(30), SHAPE.STArea() double, SHAPE.STLength() double
    -> FeatureMerger_2 [REQUESTOR]
DrawingType_RT (reader GEODATABASE_SDE_3)
    attributes: OBJECTID integer, DRAWINGNAME char(100), BUILDINGID char(60), FLOORCODE char(20), FLOORID char(60), SITEID char(60)
    -> BulkAttributeRenamer_6
BulkAttributeRenamer_6
    CASE_CHANGE_TYPE = lowercase
    ATTRCHOICE = All Attributes
    PATTERN_ACTION_DISP = Change Case
    -> BulkAttributeRenamer_7
BulkAttributeRenamer_7
    ATTRCHOICE = All Attributes
    REPLACE_STR = RT_
    PATTERN_ACTION_DISP = Add String Prefix
    -> FeatureMerger_2 [SUPPLIER]
FeatureMerger_2
    MERGE_TYPE = Attributes Only
    ATTR_ACCUM_MODE = Merge Supplier
    SUPPLIERS_FIRST = No
    PROCESS_DUPS = No
    IGNORE_NULLS = No
    JOIN_KEYS = @Value(FLOORID) @Value(RT_floorid) AUTO
    ATTR_CONFLICT_RES = Use Requestor
    REJECT_NULL_MISSING_KEYS = No
    MERGED -> BulkAttributeRenamer_4
BulkAttributeRenamer_4
    CASE_CHANGE_TYPE = lowercase
    ATTRCHOICE = All Attributes
    PATTERN_ACTION_DISP = Change Case
    -> FloorMergeSpaces [REQUESTOR]
A-AREA-DATA (reader ACAD_1)
    -> Tester
Tester
    BOOL_OP = OR
    TEST_MODE = Automatic
    TEST_DESCRIPTION = ""
    TEST_CLAUSE = TEST $(FEATURE_TYPES_READ) CONTAINS @Value(fme_feature_type)
    PASSED -> AttributeCopier
AttributeCopier
    ATTR_LIST = drawing,fme_basename
    -> Reprojector
Reprojector
    INTERPOLATION_TYPE_NAME = Nearest Neighbor
    SOURCE = $(SourceCoordinateSystem)
    STROKE_ARCS = Yes
    RASTER_CELL_SIZE = Preserve Cells
    DEST = EPSG:3857
    REPROJECTED -> ArcSDEGridSnapper
ArcSDEGridSnapper
    ZSCALE = 10000
    XMIN = -20037700
    PRECISION_DISPLAY = High precision (53 bit)
    SCALE = 10000
    YMIN = -30241100
    ZMIN = -10000
    OUTPUT_INT = No
    SNAPPED -> AttributeSplitter
AttributeSplitter
    ATTR_NAME = fme_basename
    TRIM_OPTION = Both
    DROP_EMPTY_PARTS = Yes
    DELIMITER = RT-
    LIST_NAME = _dwgpart
    -> Setfloorid
Setfloorid: StringConcatenator
    VAL_ATTR = floorid
    PARM_LINE = @Value(_dwgpart{0})_@Value(_dwgpart{1})
    -> FloorMergeCAD [REQUESTOR]
Floor_Level (reader GEODATABASE_SDE_1)
    attributes: geodb_oid integer, OBJECTID integer, SITEID char(60), FLOORCODE char(20), FLOORLEVEL integer, NAMELONG char(100), NAMESHORT char(50), HASFLOORPLANLINES char(3), SOURCEID char(30), HASINTERIORSPACES char(3), LASTUPDATE date, BLDGCODE char(50), SCHELEV integer, CALCROT double, SHAPE.STLength() double, SENSITIVITY char(20), SOURCEDWG char(100), HASFLOORAREA char(3), GROUNDELEV double, BUILDINGID char(60), STACKLEVEL integer, LASTEDITOR char(30), SHAPE.STArea() double, FLOORID char(60), BLDGNAME char(100)
    -> AttributeExposer_3
AttributeExposer_3
    ATTR_LIST = fme_feature_type
    -> BulkAttributeRenamer
BulkAttributeRenamer
    CASE_CHANGE_TYPE = lowercase
    ATTRCHOICE = All Attributes
    PATTERN_ACTION_DISP = Change Case
    -> AttributeCopier_2
AttributeCopier_2
    ATTR_LIST = floorid,tofloor,"",floorid,fromfloor,""
    -> _floorelev
_floorelev: ExpressionEvaluator
    EXPRESSION = @Value($(elevName))
    VAL_ATTR = _floorelev
    -> convertMeters
convertMeters: ExpressionEvaluator
    EXPRESSION = @Value(_floorelev) * 0.3048
    VAL_ATTR = _floorelev
    -> FloorMergeSpaces [SUPPLIER]
    -> FloorMergeCAD [SUPPLIER]
    -> SetZValues [FloorInfo]
FloorMergeSpaces: FeatureMerger
    SUPPLIER_PREFIX_DUMMY = YES
    PROCESS_DUPS = No
    MERGE_TYPE = Attributes Only
    JOIN_KEYS = @Value(floorid) @Value(floorid) AUTO
    SUPPLIERS_FIRST = No
    IGNORE_NULLS = Yes
    MERGED -> RouteConstructor [InteriorSpace]
    MERGED -> SpatialFilter [Filter]
FloorMergeCAD: FeatureMerger
    SUPPLIER_PREFIX_DUMMY = YES
    PROCESS_DUPS = No
    MERGE_TYPE = Attributes Only
    JOIN_KEYS = @Value(floorid) @Value(floorid) AUTO
    SUPPLIERS_FIRST = No
    IGNORE_NULLS = Yes
    MERGED -> gzFieldCalculator [AddFieldsValues_Input_1]
    NOT_MERGED -> FeatureMerger_NotMerged_2
gzFieldCalculator
    AddFieldsValues_Output_1 -> BulkAttributeRenamer_2
BulkAttributeRenamer_2
    CASE_CHANGE_TYPE = lowercase
    ATTRCHOICE = All Attributes
    PATTERN_ACTION_DISP = Change Case
    -> TestFilter
TestFilter
    TEST_LIST = BOOL_OP,OR,COMPOSITE_TEST,<Unused>,TEST_CLAUSE,"TEST @Value(fme_feature_type) = RT_LineInterior",RT_LineInterior,BOOL_OP,OR,COMPOSITE_TEST,<Unused>,TEST_CLAUSE,"TEST @Value(fme_feature_type) = RT_DoorPoint",RT_DoorPoint,BOOL_OP,OR,COMPOSITE_TEST,<Unused>,TEST_CLAUSE,"TEST @Value(fme_feature_type) = RT_Stop",RT_Stop,BOOL_OP,OR,COMPOSITE_TEST,<Unused>,TEST_CLAUSE,"TEST @Value(fme_feature_type) = RT_LineTransition",RT_LineTransition
    DEFAULT_VALUE = <UNFILTERED>
    RT_LineInterior -> RouteConstructor [RT_LineInterior]
    RT_LineInterior -> SpatialFilter [Candidate]
    RT_DoorPoint -> RouteConstructor [RT_ConnectionPoints]
    RT_Stop -> RouteConstructor [RT_ConnectionPoints]
    RT_LineTransition -> SpatialFilter [Candidate]
Note: Construct connection lines and room pts/location
RouteConstructor
    doorDist = 0.46
    lineDist = 0.5
    RT_RoomPoint -> SetZValues [RT_Others]
    RT_LineRmConnector -> SetZValues [RT_Others]
    RT_Point -> SetZValues [RT_Others]
SpatialFilter
    MERGE_ATTRS = Yes
    PREDATTR = _predicate
    PREDICATES = CROSSES CONTAINS
    ATTR_PREFIX = _rm
    PASS_CRITERIA = Pass Against One Filter
    GROUP_BY = floorid
    CURVE_BOUNDARY_RULE_PARAM = Default Rule
    USE_BOUNDING_BOX = No
    BASE_TYPE = Single Filter
    PASSED -> spaceid
    FAILED -> TestFilter_2
spaceid: AttributeCreator
    ATTR_LIST = spaceid,@Value(_rmspaceid)
    -> BulkAttributeRemover
Note: Waypoints for rooms in the route constructor, Line Transition Waypoints are in SetZValues
BulkAttributeRemover
    ATTR_EXP = _rm*
    -> TestFilter_2
TestFilter_2
    TEST_LIST = BOOL_OP,OR,COMPOSITE_TEST,<Unused>,TEST_CLAUSE,"TEST @Value(fme_feature_type) = RT_LineInterior",RT_LineInterior,BOOL_OP,OR,COMPOSITE_TEST,<Unused>,TEST_CLAUSE,"TEST @Value(fme_feature_type) = RT_LineTransition",RT_LineTransition
    DEFAULT_VALUE = <UNFILTERED>
    RT_LineInterior -> SetZValues [RT_LineInterior]
    RT_LineTransition -> SetZValues [RT_LineTransition]
Note: set z value for everything,
SetZValues
    SPACEID = @Value(spaceid)
    BUILDINGID = @Value(buildingid)
    STACKLEVEL = @Value(stacklevel)
    3DOutput -> Snapper
Snapper
    EXTEND_LINES = NEVER
    SNAPTYPE_PARAM = End Point Snapping
    SAVE_SHORT_LINES = No
    GROUP_BY = floorid
    TOLERANCE = .01
    SNAPPED -> BulkAttributeRemover_2
    UNTOUCHED -> BulkAttributeRemover_2
BulkAttributeRemover_2
    ATTR_EXP = _*
    -> BulkAttributeRenamer_3
BulkAttributeRenamer_3
    CASE_CHANGE_TYPE = UPPERCASE
    ATTRCHOICE = All Attributes
    PATTERN_ACTION_DISP = Change Case
    -> gzSourceTargetQA [SourceTargetQA_Input_1]
gzSourceTargetQA
    SourceTargetQA_Output_1 -> AttributeExposer
AttributeExposer
    ATTR_LIST = FLOORID
    -> gzWriteData [gzFeatures]
gzWriteData
    IgnoreErrors = False
    HASERRORS = @Value(HasErrors)
    GroupBy = @Value(FLOORID)
    gzLogWriter -> gzLog (writer GEODATABASE_SDE_4)
    gzFeatureWriter -> TruncateFirst
    gzErrorWriter -> gzError (writer GEODATABASE_SDE_4)
gzLog (writer GEODATABASE_SDE_4)
    attributes: geodb_oid integer, objectid integer, procname char(255), loadtime date, loadname char(255), dataset char(255), completed smallint, loaduser char(255), activeflag char(255)
TruncateFirst: TestFilter
    TEST_LIST = BOOL_OP,OR,COMPOSITE_TEST,<Unused>,TEST_CLAUSE,"TEST $(truncate) = Y",Y,BOOL_OP,OR,COMPOSITE_TEST,<Unused>,TEST_CLAUSE,"TEST $(truncate) = N",N
    DEFAULT_VALUE = <UNFILTERED>
    Y -> Features (writer GEODATABASE_SDE_4)
    N -> Features00 (writer GEODATABASE_SDE_4)
Features (writer GEODATABASE_SDE_4)
Features00 (writer GEODATABASE_SDE_4)
gzError (writer GEODATABASE_SDE_4)
    attributes: geodb_oid integer, objectid integer, procname char(255), sourcename char(255), srcidfield char(255), srcidval char(255), dataset char(255), reason char(255), erruser char(255), errtime date, activeflag char(255)
FeatureMerger_NotMerged_2: Logger
    MESSAGE = Feature is missing floor data:
    MAXCOORDS = 20
    MAXFEATS = 20000

FME custom transformer gzBuildingAngle

Parameters:
- BUILDINGID =   # Enter the Building ID

INPUT (input)
    -> Chopper_2
    -> FeatureMerger_3 [REQUESTOR]
Chopper_2
    MAX = 2
    CHOPPED -> LengthCalculator_2
LengthCalculator_2
    DIM = 2
    MULT = 1
    LEN_ATTR = _length
    -> StatisticsCalculator_2
StatisticsCalculator_2
    RANGE_ATTR = _range
    COUNT_ATTR = _count
    MEDIAN_ATTR = _median
    SUM_ATTR = _sum
    MEAN_ATTR = _mean
    NUMERIC_ATTR = _numeric_count
    MODE_ATTR = _mode
    STDEV_ATTR = _stdev
    STATS_ATTR = _length
    MIN_ATTR = _min
    MAX_ATTR = _max
    PASS_THROUGH = Yes
    STATISTICS -> TestFilter_6
TestFilter_6
    TEST_LIST = BOOL_OP,OR,COMPOSITE_TEST,<Unused>,TEST_CLAUSE,"TEST ""@Value(_length)"" = ""@Value(_max)""",_length = _max
    DEFAULT_VALUE = <UNFILTERED>
    _length = _max -> CoordinateExtractor_4
CoordinateExtractor_4
    IND = 0
    Z_DEFAULT = -9999
    Y_ATTR = _y1
    Z_ATTR = _z
    X_ATTR = _x1
    -> CoordinateExtractor_6
CoordinateExtractor_6
    IND = 1
    Z_DEFAULT = -9999
    Y_ATTR = _y2
    Z_ATTR = _z
    X_ATTR = _x2
    -> TestFilter_4
TestFilter_4
    TEST_LIST = BOOL_OP,OR,COMPOSITE_TEST,<Unused>,TEST_CLAUSE,"TEST ""@Value(_y2)"" >= ""@Value(_y1)""",_y2 >= _y1
    DEFAULT_VALUE = <UNFILTERED>
    _y2 >= _y1 -> ExpressionEvaluator_7
    <UNFILTERED> -> ExpressionEvaluator_4
Note: Calculate angle of the longest side
ExpressionEvaluator_7
    EXPRESSION = @atan2(@Value(_x1)-@Value(_x2),@Value(_y1)-@Value(_y2))*180.0/(22/7.0)
    VAL_ATTR = _angle
    -> ExpressionEvaluator_8
ExpressionEvaluator_4
    EXPRESSION = @atan2(@Value(_x2)-@Value(_x1),@Value(_y2)-@Value(_y1))*180.0/(22/7.0)
    VAL_ATTR = _angle
    -> ExpressionEvaluator_8
ExpressionEvaluator_8
    EXPRESSION = @Value(_angle) + 90.0
    VAL_ATTR = _angle
    -> TestFilter_5
TestFilter_5
    TEST_LIST = BOOL_OP,OR,COMPOSITE_TEST,<Unused>,TEST_CLAUSE,"TEST ""@Value(_angle)"" > ""180.0""",_angle > 180.0
    DEFAULT_VALUE = <UNFILTERED>
    _angle > 180.0 -> ExpressionEvaluator_10
    <UNFILTERED> -> Sorter_2
ExpressionEvaluator_10
    EXPRESSION = @Value(_angle) -180.0
    VAL_ATTR = _angle
    -> Sorter_2
Sorter_2
    SORT_PARM = _length NUMERIC DESCENDING
    SORTED -> FeatureMerger_3 [SUPPLIER]
FeatureMerger_3
    REFEEATTR = $(BUILDINGID)
    PROCESS_DUPS = No
    MERGE_TYPE = Attributes Only
    REFERATTR = $(BUILDINGID)
    BUILD_INCOMPLETE = No
    COMPLETE -> GeometryExtractor_2
GeometryExtractor_2
    KIND_LONG = FME Binary
    ATTR = _geometry
    -> CenterOfGravityReplacer
CenterOfGravityReplacer
    CENTEROFGRAVITY -> CoordinateExtractor_3
CoordinateExtractor_3
    IND = 0
    Z_DEFAULT = -9999
    Y_ATTR = YCENTER
    Z_ATTR = _z
    X_ATTR = XCENTER
    -> GeometryReplacer
GeometryReplacer
    KIND_LONG = FME Binary
    ATTR = _geometry
    -> AttributeCreator
Note: Calculate X and Y Center Point
AttributeCreator
    ATTR_LIST = MODANGLE,0,SPACING,50,MARGIN,.2,HULLROT,@Value(_angle)
    -> OUTPUT (output)
OUTPUT (output)

FME custom transformer gzAggregateLines
Clean geometries and Aggregate Floorplan lines into _Optimized features

INPUT (input)
    -> CoordinateCounter
CoordinateCounter
    CNT_ATTR = _coordcount
    -> LengthCalculator_2
LengthCalculator_2
    DIM = 2
    MULT = 1
    LEN_ATTR = _length
    -> TestFilter_6
TestFilter_6
    TEST_LIST:
      BOOL_OP,AND,COMPOSITE_TEST,<Unused>,TEST_CLAUSE,"TEST ""@Value(_coordcount)"" >= ""2""
      TEST ""@Value(_length)"" >= "".001""",2pts & length > .01
    DEFAULT_VALUE = <UNFILTERED>
    2pts & length > .01 -> SelfIntersectChecker
SelfIntersectChecker
    NotSelfIntersecting -> GeometryCoercer
    SelfIntersecting -> SelfIntersector
SelfIntersector
    SEG_ATTR = _segments
    SELF_INTERSECTED -> GeometryCoercer
GeometryCoercer
    KIND = fme_line
    COERCED -> Aggregator_2
Aggregator_2
    ORDERED = No
    CONTAIN_INDIVID_GEOMS = No
    SEP = ,
    ACCUM_ATTRS_NAME = Yes
    GROUP_BY = FLOORID
    AGGREGATE -> OUTPUT (output)
OUTPUT (output)

FME custom transformer SelfIntersectChecker
Separates self-intersecting features from the rest of input. This custom transformer does not change the geometry of self-intersecting features. If you want to remove self-intersections, try the " SelfIntersector " transformer.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Input (input)
    -> PartCounter
PartCounter
    COUNT_ATTR = _part_count1
    RECURSIVE_PARAM = No
    -> COUNTER
COUNTER: Counter
    SCOPE = Local
    CNT_ATTR = _selfID
    DOMAIN = counter
    START = 0
    -> GeometryExtractor
GeometryExtractor
    KIND_LONG = OGC Well Known Text
    ATTR = _geometry
    OGCVERSION = 1.2
    -> SelfIntersector
SelfIntersector
    SEG_ATTR = _segments
    SELF_INTERSECTED -> DuplicateRemover
DuplicateRemover
    KEYATTR = _selfID
    UNIQUE -> TESTER
TESTER: Tester
    BOOL_OP = OR
    TEST_LIST = &_segments,>,1
    TEST_MODE = NUMERIC
    TEST_CLAUSE = TEST @Value(_segments) > 1
    PASSED -> GeometryReplacer
    FAILED -> PartCounter_2
PartCounter_2
    COUNT_ATTR = _part_count2
    RECURSIVE_PARAM = No
    -> TESTER_2
TESTER_2: Tester
    BOOL_OP = OR
    TEST_LIST = &_part_count1,=,&_part_count2
    TEST_MODE = Automatic
    TEST_CLAUSE = TEST @Value(_part_count1) = @Value(_part_count2)
    PASSED -> ATTRIBUTEREMOVER
    FAILED -> GeometryReplacer
ATTRIBUTEREMOVER: AttributeRemover
    REMOVE_ATTRS = _selfID,_geometry,_segments
    -> NotSelfIntersecting (output)
NotSelfIntersecting (output)
GeometryReplacer
    KIND_LONG = OGC Well Known Text
    ATTR = _geometry
    -> ATTRIBUTEREMOVER_2
ATTRIBUTEREMOVER_2: AttributeRemover
    REMOVE_ATTRS = _selfID,_geometry,_segments
    -> SelfIntersecting (output)
SelfIntersecting (output)

FME custom transformer RouteConstructor

Parameters:
- lineDist = 0.5   # Line distance to test
- doorDist = 0.46   # Distance to search from doors to spaces

InteriorSpace (input)
    -> AttributeExposer
AttributeExposer
    ATTR_LIST = buildingid,floorcode,floorid,lasteditor,lastupdate,roomnumber,siteid,sourcedwg,sourceid,spacearea,spaceclass,spaceid,fme_basename,_floorelev
    -> SpaceNeighborFinder [CANDIDATE]
    -> NeighborFinder [BASE]
    -> InsidePointReplacer
InsidePointReplacer
    INSIDEPOINT -> RT_RoomPoint
Note: Create a separate room point
RT_RoomPoint: AttributeCreator
    ATTR_LIST = fme_feature_type,RT_RoomPoint
    -> CoordinateExtractor_Room
CoordinateExtractor_Room
    IND = 0
    Z_DEFAULT = 0
    Y_ATTR = _y0
    Z_ATTR = _z0
    X_ATTR = _x0
    -> FeatureMerger_4 [REQUESTOR]
    -> FeatureMerger [REQUESTOR]
RT_LineInterior (input)
    -> AttributeExposer_4
AttributeExposer_4
    ATTR_LIST = buildingid,floorcode,floorid,lasteditor,lastupdate,siteid,sourcedwg,sourceid,fme_basename,_floorelev
    -> GeometryExtractor
GeometryExtractor
    KIND_LONG = FME Binary
    ATTR = _linegeometry
    -> NeighborFinder [CANDIDATE]
    -> BulkAttributeRemover_3
BulkAttributeRemover_3
    ATTR_EXP = autocad*
    -> BulkAttributeRemover
Note: Adjust room point to line where line exists
BulkAttributeRemover
    ATTR_EXP = _lines{}*
    -> NeighborFinder_3 [CANDIDATE]
Note: need to look .5m to find doors on other side of walls
NeighborFinder
    TREAT_POLYGON_AS = Lines
    MAX = $(lineDist)
    INSERT_VERTEX = No
    CLOSE_LIST_NAME = _lines
    GROUP_BY = floorid
    CANDIDATES_FIRST = No
    MATCHED -> ListElementCounter
    UNMATCHED_BASE -> NeighborFinder_UnmatchedBase
ListElementCounter
    CNT_ATTR = _line_count
    LIST_NAME = _lines{}
    -> OverlappingLine
Note: Connect to space{0} or space{1}. Only 1 of the spaces should have 1 line....
OverlappingLine: TestFilter
    TEST_LIST = BOOL_OP,OR,COMPOSITE_TEST,<Unused>,TEST_CLAUSE,"TEST @Value(_line_count) > 1",> 1,BOOL_OP,OR,COMPOSITE_TEST,<Unused>,TEST_CLAUSE,"TEST @Value(_line_count) <= 1",<= 1
    DEFAULT_VALUE = <UNFILTERED>
    > 1 -> FeatureMerger [SUPPLIER]
    <= 1 -> FeatureMerger_3 [REQUESTOR]
    <= 1 -> FeatureMerger_2 [REQUESTOR]
FeatureMerger
    SUPPLIER_PREFIX_DUMMY = YES
    PROCESS_DUPS = No
    MERGE_TYPE = Attributes Only
    JOIN_KEYS = @Value(spaceid) @Value(spaceid) AUTO
    SUPPLIERS_FIRST = No
    IGNORE_NULLS = Yes
    MERGED -> NeighborFinder_3 [BASE]
    NOT_MERGED -> gzFieldCalculator_2 [AddFieldsValues_Input_1]
NeighborFinder_3
    TREAT_POLYGON_AS = Lines
    MAX = 30
    INSERT_VERTEX = No
    TEST_LIST_NAME = _test
    CLOSE_LIST_NAME = _close
    GROUP_BY = floorid
    CANDIDATES_FIRST = No
    MATCHED -> VertexCreator_3
Note: Untoched room points
VertexCreator_3
    MODE_NAME = Replace with Point
    YVAL = @Value(_closest_candidate_y)
    XVAL = @Value(_closest_candidate_x)
    ZVAL = @Value(_z0)
    -> gzFieldCalculator_2 [AddFieldsValues_Input_1]
gzFieldCalculator_2
    AddFieldsValues_Output_1 -> BulkAttributeRemover_2
BulkAttributeRemover_2
    ATTR_EXP = _close*
    -> BulkAttributeRemover_7
BulkAttributeRemover_7
    ATTR_EXP = Close*
    -> RT_RoomPoint (output)
    -> TestFilter
RT_RoomPoint (output)
TestFilter
    TEST_LIST = BOOL_OP,OR,COMPOSITE_TEST,<Unused>,TEST_CLAUSE,"TEST @Value(roomnumber) CONTAINS EL",@Value(roomnumber) CONTAINS EL
    DEFAULT_VALUE = <UNFILTERED>
    @Value(roomnumber) CONTAINS EL -> WaypointName_2
WaypointName_2: AttributeCreator
    ATTR_LIST = name,@Value(roomnumber) Elevator,waypointtype,Elevator
    -> RT_WayPoint
RT_WayPoint: AttributeCreator
    ATTR_LIST = fme_feature_type,RT_Waypoint
    -> RT_Point (output)
NeighborFinder_UnmatchedBase: Logger
    MESSAGE = Feature is:
    MAXCOORDS = 20
    MAXFEATS = 20
RT_ConnectionPoints (input)
    -> AttributeExposer_3
AttributeExposer_3
    ATTR_LIST = buildingid,floorcode,floorid,lasteditor,lastupdate,siteid,sourcedwg,sourceid,fme_basename,_floorelev
    -> CoordinateExtractor_Door
CoordinateExtractor_Door
    IND = 0
    Z_DEFAULT = 0
    Y_ATTR = _y1
    Z_ATTR = _z1
    X_ATTR = _x1
    -> SpaceNeighborFinder [BASE]
Note: look 1.5m to find spaces
SpaceNeighborFinder: NeighborFinder
    TREAT_POLYGON_AS = Lines
    MAX = $(doorDist)
    INSERT_VERTEX = No
    CLOSE_LIST_NAME = CloseList
    GROUP_BY = floorid
    CANDIDATES_FIRST = No
    MATCHED -> AttributeCreator_32
    UNMATCHED_BASE -> RT_Point (output)
AttributeCreator_32
    ATTR_LIST = spaceid1,@Value(CloseList{0}.spaceid),spaceid2,@Value(CloseList{1}.spaceid)
    -> FeatureMerger_2 [SUPPLIER]
    -> FeatureMerger_3 [SUPPLIER]
    -> ListIndexer_3
Note: Only create lines for spaces with no exiisting lines.
FeatureMerger_2
    SUPPLIER_PREFIX_DUMMY = YES
    PROCESS_DUPS = Yes
    MERGE_TYPE = Attributes Only
    GEOM_TYPE = Build Polygons
    JOIN_KEYS = @Value(spaceid) @Value(spaceid1) AUTO
    SUPPLIERS_FIRST = No
    IGNORE_NULLS = Yes
    MERGED -> AttributeRenamer
AttributeRenamer
    ATTR_LIST = spaceid1,spaceid,""
    -> FeatureMerger_4 [SUPPLIER]
FeatureMerger_3
    SUPPLIER_PREFIX_DUMMY = YES
    PROCESS_DUPS = Yes
    MERGE_TYPE = Attributes Only
    GEOM_TYPE = Build Polygons
    JOIN_KEYS = @Value(spaceid) @Value(spaceid2) AUTO
    SUPPLIERS_FIRST = No
    IGNORE_NULLS = Yes
    MERGED -> AttributeRenamer_2
AttributeRenamer_2
    ATTR_LIST = spaceid2,spaceid,""
    -> FeatureMerger_4 [SUPPLIER]
FeatureMerger_4
    SUPPLIER_PREFIX_DUMMY = YES
    PROCESS_DUPS = No
    MERGE_TYPE = Attributes Only
    JOIN_KEYS = @Value(spaceid) @Value(spaceid) AUTO
    SUPPLIERS_FIRST = No
    IGNORE_NULLS = Yes
    MERGED -> VertexCreator
VertexCreator
    MODE_NAME = Replace with Point
    YVAL = @Value(_y0)
    XVAL = @Value(_x0)
    ZVAL = @Value(_z0)
    -> VertexCreator_2
Note: create the line geometry from space point to door
VertexCreator_2
    MODE_NAME = Add Point
    YVAL = @Value(_y1)
    XVAL = @Value(_x1)
    ZVAL = @Value(_z1)
    -> AttributeCreator
AttributeCreator
    ATTR_LIST = fme_feature_type,RT_LineRmConnector
    -> gzFieldCalculator_3 [AddFieldsValues_Input_1]
gzFieldCalculator_3
    AddFieldsValues_Output_1 -> BulkAttributeRemover_5
BulkAttributeRemover_5
    ATTR_EXP = Close*
    -> RT_LineRmConnector (output)
RT_LineRmConnector (output)
Note: This is door points and stops
ListIndexer_3
    LIST_ATTR = CloseList{}
    INDEX = 0
    -> BulkAttributeRemover_6
Note: apparently no waypoints on stops or doors, but need for elevator room points
BulkAttributeRemover_6
    ATTR_EXP = Close*
    -> RT_Point (output)
RT_Point (output)

FME custom transformer gzTiltRooms
Tilt Rooms in floorplans to create a pseudo-isometric view of the rooms and floors

Parameters:
- pBUILDINGID = 1327   # Enter the Building Identifier
- pFLOORID = 1327_01   # Enter the FacFloor Number

INPUT (input)
    -> DuplicateRemover
    -> FeatureMerger_2 [REQUESTOR]
    -> DuplicateRemover_2
DuplicateRemover_2
    KEYATTR = $(pBUILDINGID)
    UNIQUE -> BldgReader [INITIATOR]
BldgReader: FeatureReader
    DATASET = sde
    SUPPORTED_SPATIAL_INTERACTIONS = ENVELOPE_INTERSECT%INTERSECTS%CONTAINS%CROSSES%DISJOINT%EQUALS%OVERLAPS%TOUCHES%WITHIN
    FORMAT = GEODATABASE_SDE
    GEODATABASE_SDE_SPLIT_COMPLEX_EDGES = no
    GEODATABASE_SDE_RESOLVE_SUBTYPE_NAMES = yes
    ATTRIBUTES = DBO.Building_Outline_Tilt,"geodb_oid,OBJECTID,BUILDINGID,HULLROT,BLDGHEIGHT,SPACING,MARGIN,XCENTER,YCENTER,SOURCEID,SOURCEDWG,IN_DATE,LAST_USER,GlobalID,SHAPE.STArea(),SHAPE.STLength()"
    GEODATABASE_SDE_IGNORE_RELATIONSHIP_INFO = yes
    GEODATABASE_SDE_RESOLVE_DOMAINS = no
    GEODATABASE_SDE_TRANSLATE_SPATIAL_DATA_ONLY = no
    GEODATABASE_SDE_SPLIT_MULTI_PART_ANNOS = no
    GEODATABASE_SDE_REMOVE_TABLE_QUALIFIER = YES
    GEODATABASE_SDE_CONNECTION_FILE = $(FME_MF_DIR)GIS Production.sde
    GEODATABASE_SDE_TABLELIST = DBO.Building_Outline_Tilt
    COMBINE_ATTRS = Keep result attributes only
    GEODATABASE_SDE_IGNORE_NETWORK_INFO = yes
    GEODATABASE_SDE_VERSION_TYPE = Connect using a Transactional Version
    GEODATABASE_SDE_CONNECTION = Connection File
    GEODATABASE_SDE_VERSION = SDE.DEFAULT
    GEODATABASE_SDE_WHERE = BUILDINGID=$(pBUILDINGID)
    COMBINE_GEOM = Keep result geometry only
    FEATURETYPES = DBO.Building_Outline_Tilt
    DBO.Building_Outline_Tilt -> BoundsExtractor_2
BoundsExtractor_2
    XMIN = _xmin
    ZMAX = _zmax
    XMAX = _xmax
    YMIN = _ymin
    YMAX = _ymax
    ZMIN = _zmin
    -> FeatureMerger_2 [SUPPLIER]
FeatureMerger_2
    SUPPLIER_PREFIX_DUMMY = YES
    PROCESS_DUPS = No
    MERGE_TYPE = Attributes Only
    JOIN_KEYS = @Value(BUILDINGID) $(pBUILDINGID)
    SUPPLIERS_FIRST = No
    IGNORE_NULLS = Yes
    MERGED -> FeatureMerger_3 [REQUESTOR]
DuplicateRemover
    KEYATTR = $(pBUILDINGID)
    UNIQUE -> FloorsReader [INITIATOR]
FloorsReader: FeatureReader
    DATASET = sde
    SUPPORTED_SPATIAL_INTERACTIONS = ENVELOPE_INTERSECT%INTERSECTS%CONTAINS%CROSSES%DISJOINT%EQUALS%OVERLAPS%TOUCHES%WITHIN
    FORMAT = GEODATABASE_SDE
    GEODATABASE_SDE_SPLIT_COMPLEX_EDGES = no
    GEODATABASE_SDE_RESOLVE_SUBTYPE_NAMES = yes
    ATTRIBUTES = DBO.Active_Floor,"geodb_oid,OBJECTID,BUILDINGID,FLOOR,FLOORID,DWG_NAME,INTERIORSPACE,FLOORPLANLINE,SCHELEV,ALTITUDE,GlobalID"
    GEODATABASE_SDE_IGNORE_RELATIONSHIP_INFO = yes
    GEODATABASE_SDE_RESOLVE_DOMAINS = no
    GEODATABASE_SDE_TRANSLATE_SPATIAL_DATA_ONLY = no
    GEODATABASE_SDE_SPLIT_MULTI_PART_ANNOS = no
    GEODATABASE_SDE_REMOVE_TABLE_QUALIFIER = NO
    GEODATABASE_SDE_CONNECTION_FILE = $(FME_MF_DIR)GIS Production.sde
    GEODATABASE_SDE_TABLELIST = DBO.Active_Floor
    COMBINE_ATTRS = In case of conflict, keep result attributes
    GEODATABASE_SDE_IGNORE_NETWORK_INFO = yes
    GEODATABASE_SDE_VERSION_TYPE = Connect using a Transactional Version
    GEODATABASE_SDE_CONNECTION = Connection File
    GEODATABASE_SDE_VERSION = SDE.DEFAULT
    GEODATABASE_SDE_WHERE = BUILDINGID=$(pBUILDINGID)
    COMBINE_GEOM = In case of conflict, keep aggregate of INITIATOR and result geometry
    FEATURETYPES = DBO.Active_Floor
    DBO.Active_Floor -> AttributeCopier_3
AttributeCopier_3
    ATTR_LIST = STACKLEVEL,SCHELEV
    -> FeatureMerger_3 [SUPPLIER]
FeatureMerger_3
    SUPPLIER_PREFIX_DUMMY = YES
    PROCESS_DUPS = No
    MERGE_TYPE = Attributes Only
    JOIN_KEYS = @Value(FLOORID) $(pFLOORID)
    SUPPLIERS_FIRST = No
    IGNORE_NULLS = Yes
    MERGED -> ExpressionEvaluator_2
ExpressionEvaluator_2
    EXPRESSION = @Value(HULLROT) + 15.0
    VAL_ATTR = CALCULATED_ROTATION
    -> Rotator
Rotator
    ANGLE = @Value(CALCULATED_ROTATION)
    XORIG = @Value(_xmin)
    YORIG = @Value(_ymin)
    ROTATED -> Y_Base
Y_Base: ExpressionEvaluator
    EXPRESSION = @Value(_ymin) + (@Value(SPACING) * @Value(STACKLEVEL))
    VAL_ATTR = _yBase
    -> tilt_Space
tilt_Space: ExpressionEvaluator
    EXPRESSION = @Value(BLDGHEIGHT) / (@Value(SPACING)+0.00001)
    VAL_ATTR = _tiltSpace
    -> Chopper
Chopper
    MAX = 1
    CHOPPED -> CoordinateExtractor
CoordinateExtractor
    IND = 0
    Z_DEFAULT = -9999
    Y_ATTR = _y
    Z_ATTR = _z
    X_ATTR = _x
    -> tilt_y
tilt_y: ExpressionEvaluator
    EXPRESSION = @Value(_yBase) + ((@Value(_y) - @Value(_ymin)) / @Value(_tiltSpace)) * (1 - @Value(MARGIN))
    VAL_ATTR = _tiltY
    -> 2DPointReplacer
2DPointReplacer
    XVALATTR = @Value(_x)
    YVALATTR = @Value(_tiltY)
    POINT -> PointConnector
PointConnector
    BREAKATTR = FACROOM
    LINE -> GeometryCoercer_2
    POLYGON -> GeometryCoercer_2
GeometryCoercer_2
    KIND = fme_polygon
    CHECKZ = No
    COERCED -> SliverRemover_2
SliverRemover_2
    REPAIR_METHOD = Longest Boundary
    REPAIRED -> OUTPUT (output)
OUTPUT (output)

FME custom transformer SetZValues

Parameters:
- SPACEID = @Value(spaceid)   # spaceid
- BUILDINGID = @Value(buildingid)   # buildingid
- STACKLEVEL = @Value(stacklevel)   # stacklevel

RT_Others (input)
    -> AttributeExposer_4
Note: Points and room connectors
AttributeExposer_4
    ATTR_LIST = autocad_layer,_floorelev,floorid,ACTIVE,ADA,buildingid,emergency,fitness,floorcode,ispublic,name,roomnumber,spaceid,fme_basename,fme_feature_type
    -> FeatureMerger_4 [REQUESTOR]
RT_LineInterior (input)
    -> AttributeExposer
Note: Interior Lines
AttributeExposer
    ATTR_LIST = autocad_layer,_floorelev,floorid,spaceid,fme_basename
    -> FeatureMerger_4 [REQUESTOR]
RT_LineTransition (input)
    -> AttributeExposer_2
AttributeExposer_2
    ATTR_LIST = autocad_layer,_floorelev,floorid,stacklevel,buildingid,spaceid,fme_basename
    -> _nextlevel
_nextlevel: AttributeCreator
    ATTR_LIST = _nextstacklevel,@Evaluate(@Value(stacklevel) + 1)
    -> FeatureMerger_3 [REQUESTOR]
FloorInfo (input)
    -> AttributeExposer_3
AttributeExposer_3
    ATTR_LIST = autocad_layer,_floorelev,floorid,stacklevel,buildingid,fme_basename,namelong,nameshort
    -> StackLevelStats
Note: Need stats for elevator construction
StackLevelStats: StatisticsCalculator
    MAX_ATTR = _maxStackLevel
    PREPEND_ATTR_NAME_CHOICE = For multiple results only
    MIN_ATTR = _minStackLevel
    STATS_ATTRS = stacklevel
    COMPUTE_HISTOGRAM = NO
    GROUP_BY = buildingid
    COMPLETE -> FeatureMerger_3 [SUPPLIER]
FeatureMerger_3
    SUPPLIER_PREFIX_DUMMY = YES
    PROCESS_DUPS = Yes
    MERGE_TYPE = Attributes Only
    GEOM_TYPE = Build Polygons
    JOIN_KEYS = @Value(buildingid) @Value(buildingid) AUTO
    SUPPLIERS_FIRST = No
    LIST_NAME = _bldg
    IGNORE_NULLS = Yes
    MERGED -> ListSearcher
Note: Transitions have z=floor z plus the portion of the height of the floor - either .5 values or .0 values based on integers in layer names
ListSearcher
    LIST_ATTR = _bldg{}.stacklevel
    INDEX_ATTR = _nextlevel
    SEARCH_TYPE = First exact match
    ATTR_VALUE = @Value(_nextstacklevel)
    FOUND -> ListIndexer
ListIndexer
    PREFIX = _next
    LIST_ATTR = _bldg{}
    INDEX = @Value(_nextlevel)
    -> FloorAttrs
FloorAttrs: AttributeCreator
    ATTR_LIST = tofloor,@Value(_nextfloorid),fromfloor,@Value(floorid),nextname,@Value(_nextnameshort),maxStackLevel,@Value(_bldg{0}._maxStackLevel),minStackLevel,@Value(_bldg{0}._minStackLevel)
    -> BulkAttributeRemover
BulkAttributeRemover
    ATTR_EXP = _bldg*
    -> CalcHeight
Note: need to calc height diff
CalcHeight: ExpressionEvaluator
    EXPRESSION = abs(@Value(_next_floorelev)-@Value(_floorelev))
    VAL_ATTR = _height
    -> AttributeSplitter
    -> DuplicateRemover
DuplicateRemover
    KEYATTR = floorid
    UNIQUE -> FeatureMerger_4 [SUPPLIER]
FeatureMerger_4
    SUPPLIER_PREFIX_DUMMY = YES
    PROCESS_DUPS = No
    MERGE_TYPE = Attributes Only
    JOIN_KEYS = @Value(floorid) @Value(floorid) AUTO
    SUPPLIER_PREFIX = _a
    SUPPLIERS_FIRST = No
    IGNORE_NULLS = Yes
    MERGED -> AttributeSplitter_3
    NOT_MERGED -> AttributeSplitter_3
AttributeSplitter_3
    ATTR_NAME = autocad_layer
    TRIM_OPTION = Both
    DROP_EMPTY_PARTS = No
    DELIMITER = -
    LIST_NAME = _parts
    -> not1.0elev
not1.0elev: Tester
    BOOL_OP = OR
    TEST_MODE = Automatic
    TEST_DESCRIPTION = ""
    TEST_CLAUSE:
      TEST @Value(_parts{2}) = 1.5
      TEST @Value(_parts{2}) = 2.0
    PASSED -> NoHeight
    FAILED -> 3DForcer
NoHeight: Tester
    BOOL_OP = OR
    TEST_MODE = Automatic
    TEST_DESCRIPTION = ""
    TEST_CLAUSE:
      TEST _a_height ATTRIBUTE_IS_MISSING ""
      TEST _a_height ATTRIBUTE_VALUE_NULL ""
    PASSED -> AttributeCreator_2
    FAILED -> ExpressionEvaluator
AttributeCreator_2
    ATTR_LIST = _a_height,1
    -> ExpressionEvaluator
ExpressionEvaluator
    EXPRESSION = ((@Value(_parts{2})-1)*@Value(_a_height)) +  @Value(_floorelev)
    VAL_ATTR = _floorelev
    -> 3DForcer
Note: force 3d for everything...
3DForcer
    ZVALATTR = @Value(_floorelev)
    KEEPZVAL = No
    -> 3DOutput (output)
AttributeSplitter
    ATTR_NAME = autocad_layer
    TRIM_OPTION = Both
    DROP_EMPTY_PARTS = No
    DELIMITER = -
    LIST_NAME = _parts
    -> startElev
startElev: ExpressionEvaluator
    EXPRESSION = ((@Value(_parts{2})-1)*@Value(_height)) +  @Value(_floorelev)
    VAL_ATTR = startElev
    -> endElev
endElev: ExpressionEvaluator
    EXPRESSION = ((@Value(_parts{3})-1)*@Value(_height)) +  @Value(_floorelev)
    VAL_ATTR = endElev
    -> 3DInterpolator
3DInterpolator
    ZENDATTR = @Value(endElev)
    ZSTARTATTR = @Value(startElev)
    -> AttributeCreator
    -> AttributeCopier
AttributeCreator
    ATTR_LIST = fme_feature_type,RT_Waypoint,waypointtype,Floor Transition
    -> coord1
    -> coord0
coord0: CoordinateExtractor
    IND = 0
    Z_DEFAULT = 0
    Y_ATTR = _y
    Z_ATTR = _z
    X_ATTR = _x
    -> AttributeCreator_3
AttributeCreator_3
    ATTR_LIST = name,@Value(nameshort) Stairs
    -> VertexCreator
coord1: CoordinateExtractor
    IND = 1
    Z_DEFAULT = 0
    Y_ATTR = _y
    Z_ATTR = _z
    X_ATTR = _x
    -> AttributeCreator_4
AttributeCreator_4
    ATTR_LIST = name,@Value(_nextnameshort) Landing
    -> VertexCreator
VertexCreator
    MODE_NAME = Replace with Point
    YVAL = @Value(_y)
    XVAL = @Value(_x)
    ZVAL = @Value(_z)
    -> AttributeCopier
AttributeCopier
    ATTR_LIST = _nextfloorid,tofloor,"",floorid,fromfloor,""
    -> 3DOutput (output)
3DOutput (output)
