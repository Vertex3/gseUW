FME workspace gseSyncToPublication.fmw

Parameters:
- GEODATABASE_SDE_IN_CONNECTION_FILE_GEODATABASE_SDE = C:\Apps\Gizinta\gseUW\ETL\serverConfig\GIS Production.sde   # Connection File
- GEODATABASE_SDE_OUT_CONNECTION_FILE_GEODATABASE_SDE = C:\Apps\Gizinta\gseUW\ETL\serverConfig\GIS Publication.sde   # Connection File
- DestDataset_GEODATABASE_SDE = sde   # Destination Esri ArcSDE Geodatabase Dataset

Readers:
- GEODATABASE_SDE_1: GEODATABASE_SDE from sde
- GEODATABASE_SDE_2: GEODATABASE_SDE from $(DestDataset_GEODATABASE_SDE)

Writers:
- GEODATABASE_SDE_3: GEODATABASE_SDE to $(DestDataset_GEODATABASE_SDE)
- GEODATABASE_SDE_4: GEODATABASE_SDE to $(DestDataset_GEODATABASE_SDE)

DBO.FloorArea (reader GEODATABASE_SDE_1)
    attributes: geodb_oid integer, OBJECTID integer, FLOORID char(60), FLOORCODE char(20), FLOORAREA double, NAMESHORT char(50), NAMELONG char(100), SCHELEV integer, GROUNDELEV double, FLOORLEVEL integer, STACKLEVEL double, SENSITIVITY char(20), CALCROT double, DDPFLOORSORT char(61), BUILDINGID char(60), SITEID char(60), SOURCEDWG char(60), LASTUPDATE date, LASTEDITOR char(30), SHAPE.STArea() double, SHAPE.STLength() double
    -> ChangeDetector [input 1]
dbo.pubFloorAreas (reader GEODATABASE_SDE_2)
    attributes: geodb_oid integer, FLOORID char(60), FLOORCODE char(20), FLOORAREA double, NAMESHORT char(50), NAMELONG char(100), SCHELEV integer, GROUNDELEV double, FLOORLEVEL integer, STACKLEVEL double, SENSITIVITY char(20), CALCROT double, DDPFLOORSORT char(61), BUILDINGID char(60), SITEID char(60), SOURCEDWG char(60), LASTUPDATE date, LASTEDITOR char(30), OBJECTID integer
    -> ChangeDetector [input 2]
ChangeDetector
    MATCHATTRS = FLOORID FLOORCODE FLOORAREA NAMESHORT NAMELONG SCHELEV GROUNDELEV FLOORLEVEL STACKLEVEL SENSITIVITY CALCROT DDPFLOORSORT BUILDINGID SITEID SOURCEDWG
    MATCH = 3D
    LENIENT_MATCH = No
    MATCH_STRATEGY = Match Selected Attributes
    EXTRA_VERTEX_TOLERANCE = .001
    BLANK_AND_MISSING_DIFFER = Yes
    ADDED -> dbo.FloorArea (writer GEODATABASE_SDE_3)
    DELETED -> dbo.FloorArea (writer GEODATABASE_SDE_4)
dbo.FloorArea (writer GEODATABASE_SDE_3)
    attributes: geodb_oid integer, OBJECTID integer, FLOORID char(50), BUILDINGID char(50), SOURCEDWG char(50), SHAPE.STArea() double, SHAPE.STLength() double
dbo.FloorArea (writer GEODATABASE_SDE_4)
    attributes: geodb_oid integer, OBJECTID integer, FLOORID char(50), BUILDINGID char(50), SOURCEDWG char(50), SHAPE.STArea() double, SHAPE.STLength() double
DBO.FloorplanLine (reader GEODATABASE_SDE_1)
    attributes: geodb_oid integer, OBJECTID integer, FLOORID char(60), FLOORCODE char(20), NAMESHORT char(50), NAMELONG char(100), SCHELEV integer, GROUNDELEV double, FLOORLEVEL integer, STACKLEVEL double, SENSITIVITY char(20), SITEID char(60), BUILDINGID char(60), SOURCELAYER char(24), SOURCEID char(30), SOURCEDWG char(60), LASTUPDATE date, LASTEDITOR char(30), SHAPE.STLength() double
    -> ChangeDetector_4 [input 1]
dbo.pubFloorplanLines (reader GEODATABASE_SDE_2)
    attributes: geodb_oid integer, FLOORID char(60), FLOORCODE char(20), NAMESHORT char(50), NAMELONG char(100), SCHELEV integer, GROUNDELEV double, FLOORLEVEL integer, STACKLEVEL double, SENSITIVITY char(20), SITEID char(60), BUILDINGID char(60), SOURCELAYER char(24), SOURCEID char(30), SOURCEDWG char(60), LASTUPDATE date, LASTEDITOR char(30), OBJECTID integer
    -> ChangeDetector_4 [input 2]
Note: Floor + Source layer for IDs
ChangeDetector_4
    MATCHATTRS = FLOORID FLOORCODE NAMESHORT NAMELONG SCHELEV GROUNDELEV FLOORLEVEL STACKLEVEL SENSITIVITY SITEID BUILDINGID SOURCELAYER SOURCEID SOURCEDWG
    MATCH = 3D
    LENIENT_MATCH = No
    MATCH_STRATEGY = Match Selected Attributes
    BLANK_AND_MISSING_DIFFER = Yes
    ADDED -> DBO.FloorplanLine (writer GEODATABASE_SDE_3)
    DELETED -> DBO.FloorplanLine (writer GEODATABASE_SDE_4)
DBO.FloorplanLine (writer GEODATABASE_SDE_3)
    attributes: geodb_oid integer, OBJECTID integer, FLOORID char(60), FLOORCODE char(20), NAMESHORT char(50), NAMELONG char(100), SCHELEV integer, GROUNDELEV double, FLOORLEVEL integer, STACKLEVEL double, SENSITIVITY char(20), SITEID char(60), BUILDINGID char(60), SOURCELAYER char(24), SOURCEID char(30), SOURCEDWG char(60), LASTUPDATE date, LASTEDITOR char(30), SHAPE.STLength() double
DBO.FloorplanLine (writer GEODATABASE_SDE_4)
    attributes: geodb_oid integer, OBJECTID integer, FLOORID char(60), FLOORCODE char(20), NAMESHORT char(50), NAMELONG char(100), SCHELEV integer, GROUNDELEV double, FLOORLEVEL integer, STACKLEVEL double, SENSITIVITY char(20), SITEID char(60), BUILDINGID char(60), SOURCELAYER char(24), SOURCEID char(30), SOURCEDWG char(60), LASTUPDATE date, LASTEDITOR char(30), SHAPE.STLength() double
DBO.InteriorSpace (reader GEODATABASE_SDE_1)
    attributes: geodb_oid integer, OBJECTID integer, SPACEID char(60), ROOMNUMBER char(30), FLOORID char(60), FLOORCODE char(20), NAMESHORT char(50), NAMELONG char(100), SCHELEV integer, GROUNDELEV double, FLOORLEVEL integer, STACKLEVEL double, SENSITIVITY char(20), SPACECLASS char(60), SPACEAREA double, BUILDINGID char(60), SITEID char(60), SOURCEID char(30), SOURCEDWG char(60), LASTUPDATE date, LASTEDITOR char(30), SHAPE.STArea() double, SHAPE.STLength() double
    -> ChangeDetector_5 [input 1]
dbo.pubInteriorSpaces (reader GEODATABASE_SDE_2)
    attributes: geodb_oid integer, SPACEID char(60), ROOMNUMBER char(30), FLOORID char(60), FLOORCODE char(20), NAMESHORT char(50), NAMELONG char(100), SCHELEV integer, GROUNDELEV double, FLOORLEVEL integer, STACKLEVEL double, SENSITIVITY char(20), SpaceClass char(60), SpaceArea double, BUILDINGID char(60), SITEID char(60), SOURCEID char(30), SOURCEDWG char(60), LASTUPDATE date, LASTEDITOR char(30), OBJECTID integer
    -> ChangeDetector_5 [input 2]
ChangeDetector_5
    MATCHATTRS = SPACEID ROOMNUMBER FLOORID FLOORCODE NAMESHORT NAMELONG SCHELEV GROUNDELEV FLOORLEVEL STACKLEVEL SENSITIVITY BUILDINGID SITEID SOURCEDWG
    MATCH = 3D
    LENIENT_MATCH = No
    MATCH_STRATEGY = Match Selected Attributes
    BLANK_AND_MISSING_DIFFER = Yes
    ADDED -> DBO.InteriorSpace (writer GEODATABASE_SDE_3)
    DELETED -> DBO.InteriorSpace (writer GEODATABASE_SDE_4)
DBO.InteriorSpace (writer GEODATABASE_SDE_3)
    attributes: geodb_oid integer, OBJECTID integer, SPACEID char(60), ROOMNUMBER char(30), FLOORID char(60), FLOORCODE char(20), NAMESHORT char(50), NAMELONG char(100), SCHELEV integer, GROUNDELEV double, FLOORLEVEL integer, STACKLEVEL double, SENSITIVITY char(20), SPACECLASS char(60), SPACEAREA double, BUILDINGID char(60), SITEID char(60), SOURCEID char(30), SOURCEDWG char(60), LASTUPDATE date, LASTEDITOR char(30), SHAPE.STArea() double, SHAPE.STLength() double
DBO.InteriorSpace (writer GEODATABASE_SDE_4)
    attributes: geodb_oid integer, OBJECTID integer, SPACEID char(60), ROOMNUMBER char(30), FLOORID char(60), FLOORCODE char(20), NAMESHORT char(50), NAMELONG char(100), SCHELEV integer, GROUNDELEV double, FLOORLEVEL integer, STACKLEVEL double, SENSITIVITY char(20), SPACECLASS char(60), SPACEAREA double, BUILDINGID char(60), SITEID char(60), SOURCEID char(30), SOURCEDWG char(60), LASTUPDATE date, LASTEDITOR char(30), SHAPE.STArea() double, SHAPE.STLength() double
DBO.InteriorSpace_Tilt (reader GEODATABASE_SDE_1)
    attributes: geodb_oid integer, OBJECTID integer, SPACEID char(60), ROOMNUMBER char(20), FLOORID char(60), FLOORCODE char(20), NAMESHORT char(50), NAMELONG char(100), FLOORLEVEL integer, STACKLEVEL double, SENSITIVITY char(20), BUILDINGID char(60), SITEID char(60), LASTUPDATE date, LASTEDITOR char(30), SHAPE.STArea() double, SHAPE.STLength() double
    -> ChangeDetector_6 [input 1]
dbo.pubInteriorSpaces_Tilt (reader GEODATABASE_SDE_2)
    attributes: geodb_oid integer, SPACEID char(60), ROOMNUMBER char(20), FLOORID char(60), FLOORCODE char(20), NAMESHORT char(50), NAMELONG char(100), FLOORLEVEL integer, STACKLEVEL double, SENSITIVITY char(20), BUILDINGID char(60), SITEID char(60), LASTUPDATE date, LASTEDITOR char(30), OBJECTID integer
    -> ChangeDetector_6 [input 2]
ChangeDetector_6
    MATCHATTRS = SPACEID ROOMNUMBER FLOORID FLOORCODE NAMESHORT NAMELONG FLOORLEVEL STACKLEVEL SENSITIVITY BUILDINGID SITEID
    MATCH = 3D
    LENIENT_MATCH = No
    MATCH_STRATEGY = Match Selected Attributes
    BLANK_AND_MISSING_DIFFER = Yes
    ADDED -> DBO.InteriorSpace_Tilt (writer GEODATABASE_SDE_3)
    DELETED -> DBO.InteriorSpace_Tilt (writer GEODATABASE_SDE_4)
DBO.InteriorSpace_Tilt (writer GEODATABASE_SDE_3)
    attributes: geodb_oid integer, OBJECTID integer, SPACEID char(60), ROOMNUMBER char(20), FLOORID char(60), FLOORCODE char(20), NAMESHORT char(50), NAMELONG char(100), FLOORLEVEL integer, STACKLEVEL double, SENSITIVITY char(20), BUILDINGID char(60), SITEID char(60), LASTUPDATE date, LASTEDITOR char(30), SHAPE.STArea() double, SHAPE.STLength() double
DBO.InteriorSpace_Tilt (writer GEODATABASE_SDE_4)
    attributes: geodb_oid integer, OBJECTID integer, SPACEID char(60), ROOMNUMBER char(20), FLOORID char(60), FLOORCODE char(20), NAMESHORT char(50), NAMELONG char(100), FLOORLEVEL integer, STACKLEVEL double, SENSITIVITY char(20), BUILDINGID char(60), SITEID char(60), LASTUPDATE date, LASTEDITOR char(30), SHAPE.STArea() double, SHAPE.STLength() double
dbo.pubInteriorSpace_Points (reader GEODATABASE_SDE_2)
    attributes: geodb_oid integer, SPACEID char(60), ROOMNUMBER char(30), FLOORID char(60), FLOORCODE char(20), NAMESHORT char(50), NAMELONG char(100), SCHELEV integer, GROUNDELEV double, FLOORLEVEL integer, STACKLEVEL double, SENSITIVITY char(20), BUILDINGID char(60), SITEID char(60), SOURCEDWG char(60), LASTUPDATE date, LASTEDITOR char(30), OBJECTID integer
    -> ChangeDetector_7 [input 2]
DBO.InteriorSpace_Point (reader GEODATABASE_SDE_1)
    attributes: geodb_oid integer, OBJECTID integer, SPACEID char(60), ROOMNUMBER char(30), FLOORID char(60), FLOORCODE char(20), NAMESHORT char(50), NAMELONG char(100), SCHELEV integer, GROUNDELEV double, FLOORLEVEL integer, STACKLEVEL double, SENSITIVITY char(20), BUILDINGID char(60), SITEID char(60), SOURCEDWG char(60), LASTUPDATE date, LASTEDITOR char(30)
    -> ChangeDetector_7 [input 1]
ChangeDetector_7
    MATCHATTRS = SPACEID ROOMNUMBER FLOORID FLOORCODE NAMESHORT NAMELONG FLOORLEVEL STACKLEVEL SENSITIVITY BUILDINGID SITEID
    MATCH = 3D
    LENIENT_MATCH = No
    MATCH_STRATEGY = Match Selected Attributes
    BLANK_AND_MISSING_DIFFER = Yes
    ADDED -> DBO.InteriorSpace_Point (writer GEODATABASE_SDE_3)
    DELETED -> DBO.InteriorSpace_Point (writer GEODATABASE_SDE_4)
DBO.InteriorSpace_Point (writer GEODATABASE_SDE_3)
    attributes: geodb_oid integer, OBJECTID integer, SPACEID char(60), ROOMNUMBER char(30), FLOORID char(60), FLOORCODE char(20), NAMESHORT char(50), NAMELONG char(100), SCHELEV integer, GROUNDELEV double, FLOORLEVEL integer, STACKLEVEL double, SENSITIVITY char(20), BUILDINGID char(60), SITEID char(60), SOURCEDWG char(60), LASTUPDATE date, LASTEDITOR char(30)
DBO.InteriorSpace_Point (writer GEODATABASE_SDE_4)
    attributes: geodb_oid integer, OBJECTID integer, SPACEID char(60), ROOMNUMBER char(30), FLOORID char(60), FLOORCODE char(20), NAMESHORT char(50), NAMELONG char(100), SCHELEV integer, GROUNDELEV double, FLOORLEVEL integer, STACKLEVEL double, SENSITIVITY char(20), BUILDINGID char(60), SITEID char(60), SOURCEDWG char(60), LASTUPDATE date, LASTEDITOR char(30)
