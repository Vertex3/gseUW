FME workspace uw_RTW_PersonMarker_Prod.fmw

Parameters:
- debug = F   # Debug?
- testfloor = 1176_B1   # Test FloorID
- testfaccode = FAB   # Test Facility Code
- testfloorcode = 0   # Test Floor Code

Readers:
- GEODATABASE_SDE_1: GEODATABASE_SDE
- GEODATABASE_SDE_2: GEODATABASE_SDE
- GEODATABASE_SDE_3: GEODATABASE_SDE

Writers:
- GEODATABASE_SDE_4: GEODATABASE_SDE
- GEODATABASE_SDE_5: GEODATABASE_SDE
- GEODATABASE_SDE_6: GEODATABASE_SDE

dbo.ROOM_ASSIGNMENT_OCCUPANT (reader GEODATABASE_SDE_2)
    attributes: FACILITY_CODE char(4), ROOM_NUMBER char(20), ORGANIZATION char(10), EMPLOYEE_ID char(9), OCCUPANT_EID char(9), OCCUPANTS_NOTES char(1073741822), CONFIRM_USER char(30), CONFIRM_DATE date, CREATE_USER char(30), CREATE_DATE date, MOD_USER char(30), MOD_DATE date, OS_USER char(30), CREATE_NETID char(30), CREATE_NETID_DATE date, MOD_NETID char(30), MOD_NETID_DATE date
    -> AttributeManager_2
AttributeManager_2
    ATTR_TABLE:
      REMOVE ORGANIZATION
      REMOVE EMPLOYEE_ID
      RENAME_SET_VALUE OCCUPANT_EID > EMPLOYEEID
      REMOVE OCCUPANTS_NOTES
      REMOVE CONFIRM_USER
      REMOVE CONFIRM_DATE
      REMOVE CREATE_USER
      REMOVE CREATE_DATE
      REMOVE MOD_USER
      REMOVE MOD_DATE
      REMOVE OS_USER
      REMOVE CREATE_NETID
      REMOVE CREATE_NETID_DATE
      REMOVE MOD_NETID
      REMOVE MOD_NETID_DATE
    -> DuplicateFilter
DuplicateFilter
    INPUT_ORDERED_CHOICE = No
    KEYATTR = FACILITY_CODE ROOM_NUMBER EMPLOYEEID
    UNIQUE -> Debug_Tester_2
Debug_Tester_2: Tester
    TEST_CLAUSE = TEST $(debug) = F
    TEST_DESCRIPTION = ""
    BOOL_OP = OR
    TEST_MODE = Automatic
    PASSED -> AttributeFilter
    FAILED -> Tester
Tester
    TEST_CLAUSE:
      TEST @Value(FACILITY_CODE) = $(testfaccode)
      TEST @Value(ROOM_NUMBER) BEGINS_WITH $(testfloorcode)
    TEST_DESCRIPTION = ""
    BOOL_OP = AND
    TEST_MODE = Automatic
    PASSED -> AttributeFilter
AttributeFilter
    ATTR_VALUES = <EMPTY>,<MISSING>,<NULL>,<UNFILTERED>,999999999
    ATTR_NAME = EMPLOYEEID
    <UNFILTERED> -> Aggregator_2
Aggregator_2
    ACCUM_ATTRS_NAME = Get Attributes From One Representative Feature
    ORDERED = No
    GROUP_BY = FACILITY_CODE ROOM_NUMBER
    SEP = ,
    AGGREGATE_TYPE = Homogeneous Collection (If Possible)
    LIST_NAME = _occupants
    MODE = Geometry - Assemble One Level
    AGGREGATE -> ListElementCounter
ListElementCounter
    CNT_ATTR = _occupant_count
    LIST_NAME = _occupants{}
    -> FeatureMerger [REQUESTOR]
DBO.FloorplanLine_ALL (reader GEODATABASE_SDE_1) [off]
    attributes: OBJECTID integer, BUILDINGKEY char(50), FLOORKEY char(50), FLOORCODE char(5), LINETYPE char(50), created_user char(255), created_date date, last_edited_user char(255), last_edited_date date, SHAPE.STLength() double
    -> Debug_Tester_5
Debug_Tester_5: Tester [off]
    TEST_CLAUSE = TEST $(debug) = F
    TEST_DESCRIPTION = ""
    BOOL_OP = OR
    TEST_MODE = Automatic
    FAILED -> Tester_2
Tester_2 [off]
    TEST_CLAUSE = TEST @Value(FLOORKEY) = $(testfloor)
    TEST_DESCRIPTION = ""
    BOOL_OP = AND
    TEST_MODE = Automatic
    PASSED -> Tester_2_Passed
Tester_2_Passed: Inspector [off]
DBO.Facility_Table (reader GEODATABASE_SDE_1)
    attributes: OBJECTID integer, FACILITY_CODE char(4), FACILITY_TYPE char(4), STATUS char(3), NAME char(20), LONG_NAME char(100), SITE char(7), YEAR_CONSTRUCTED char(4), SECTOR char(3), REGISTERED_HISTORIC_SITE char(1), LAST_MAJOR_RENOVATION_DATE date, CONSTRUCTION_TYPE char(5), WEB_PLAN char(1), OFM_CITY_CODE char(4), OFM_COUNTY_CODE char(3), OFM_LEASE_START_DATE date, OFM_LEASE_END_DATE date, OFM_SITE_CODE char(3), OFM_LEGISLATIVE_DISTRICT char(2), OFM_CONDITION char(1), OFM_SITE_ADDRESS char(40), OFM_HSR char(3), OFM_REPLACEMENT_COST_FACTOR integer, BUILDING char(3), CENTER_FACILITY_LATITUDE double, CENTER_FACILITY_LONGITUDE double, MOD_USER char(30), MOD_DATE date, OS_USER char(30), CREATE_USER char(30),
      CREATE_DATE date, LEASED_OR_OWNED char(6), FACILITY_NUMBER smallint, GROSS_SQUARE_FEET integer, CONSTRUCTION_OR_PURCHASE_COST integer, LAST_MAJOR_RENOVATION_COST integer, AGGREGATE_FACILITY_NUMBER smallint
    -> AttributeRemover_2
AttributeRemover_2
    REMOVE_ATTRS = OFM_HSR,OS_USER,LAST_MAJOR_RENOVATION_COST,NAME,CENTER_FACILITY_LONGITUDE,MOD_USER,OFM_SITE_ADDRESS,OFM_SITE_CODE,FACILITY_TYPE,MOD_DATE,SITE,OFM_LEASE_END_DATE,BUILDING,AGGREGATE_FACILITY_NUMBER,OFM_CONDITION,SECTOR,LEASED_OR_OWNED,OFM_REPLACEMENT_COST_FACTOR,CREATE_DATE,YEAR_CONSTRUCTED,OFM_LEGISLATIVE_DISTRICT,GROSS_SQUARE_FEET,CREATE_USER,OFM_CITY_CODE,CENTER_FACILITY_LATITUDE,OFM_LEASE_START_DATE,WEB_PLAN,LONG_NAME,REGISTERED_HISTORIC_SITE,OFM_COUNTY_CODE,CONSTRUCTION_OR_PURCHASE_COST,LAST_MAJOR_RENOVATION_DATE,CONSTRUCTION_TYPE,OBJECTID,STATUS
    -> FeatureMerger [SUPPLIER]
FeatureMerger
    PROCESS_DUPS = No
    MERGE_TYPE = Attributes Only
    JOIN_KEYS = @Value(FACILITY_CODE) @Value(FACILITY_CODE) AUTO
    SUPPLIERS_FIRST = No
    ATTR_ACCUM_MODE = Merge Supplier
    ATTR_CONFLICT_RES = Use Requestor
    IGNORE_NULLS = No
    LIST_NAME = occupant_room_list
    REJECT_NULL_MISSING_KEYS = No
    MERGED -> ListExploder_2
ListExploder_2
    ATTR_ACCUM_MODE = Merge Incoming List
    LIST_ATTR = _occupants{}
    INDEX_ATTR = _element_index
    ATTR_CONFLICT_RES = Use Incoming List
    ELEMENTS -> AttributeRemover_4
AttributeRemover_4
    LIST_ATTRS = occupant_room_list{} occupant_room_list{}.FACILITY_CODE occupant_room_list{}.FACILITY_NUMBER
    -> FeatureMerger_2 [REQUESTOR]
DBO.InteriorSpace_Point_ALL (reader GEODATABASE_SDE_1)
    attributes: OBJECTID integer, SPACEID char(50), ROOMNUMBER char(25), ACCESSTYPEKEY char(50), ADA char(15), ALLOCATIONPCT double, ASSIGNMENTKEY char(50), CAPACITY integer, PHYSICALCAPACITY integer, CEILINGHEIGHT double, DESCRIPTION char(255), FLOORKEY char(50), FLOORCODE char(5), GROSSAREA double, LONGNAME char(100), NETAREA double, OCCUPANCY smallint, SECTIONKEY char(50), SHORTNAME char(25), SPACESTANDARDKEY char(50), SPACETYPECAT1KEY char(5), SPACETYPECAT2KEY char(5), SPACEUSECAT1KEY char(5), SPACEUSECAT2KEY char(5), AVAILABILITY char(50), USABLE char(10), ASSIGNABLE char(10), ORGASSIGNABLE char(10), VACANCY smallint, created_date date,
      created_user char(255), last_edited_date date, last_edited_user char(255), BUILDINGKEY char(50), ASSIGNMENTCOLLEGEKEY char(3), ASSIGNMENTDEPARTMENTKEY char(7), ASSIGNMENTSUBCOLLEGE char(50)
    -> Debug_Tester_3
Debug_Tester_3: Tester
    TEST_CLAUSE = TEST $(debug) = F
    TEST_DESCRIPTION = ""
    BOOL_OP = OR
    TEST_MODE = Automatic
    PASSED -> AttributeRemover_3
    FAILED -> Tester_3
Tester_3
    TEST_CLAUSE = TEST @Value(FLOORKEY) = $(testfloor)
    TEST_DESCRIPTION = ""
    BOOL_OP = AND
    TEST_MODE = Automatic
    PASSED -> AttributeRemover_3
AttributeRemover_3
    REMOVE_ATTRS = SPACEUSECAT1KEY,SPACEUSECAT2KEY,ASSIGNMENTSUBCOLLEGE,ORGASSIGNABLE,VACANCY,last_edited_user,ASSIGNMENTDEPARTMENTKEY,SECTIONKEY,SHORTNAME,CAPACITY,created_user,GROSSAREA,ADA,SPACESTANDARDKEY,ASSIGNMENTCOLLEGEKEY,LONGNAME,SPACETYPECAT1KEY,DESCRIPTION,created_date,FLOORCODE,ACCESSTYPEKEY,ASSIGNABLE,last_edited_date,ALLOCATIONPCT,ASSIGNMENTKEY,OBJECTID,SPACETYPECAT2KEY,OCCUPANCY,USABLE,CEILINGHEIGHT,NETAREA,PHYSICALCAPACITY,AVAILABILITY
    -> FeatureMerger_2 [SUPPLIER]
FeatureMerger_2
    PROCESS_DUPS = No
    MERGE_TYPE = Attributes and Geometry
    JOIN_KEYS = @Value(FACILITY_NUMBER) @Value(BUILDINGKEY) AUTO @Value(ROOM_NUMBER) @Value(ROOMNUMBER) AUTO
    SUPPLIERS_FIRST = No
    ATTR_ACCUM_MODE = Merge Supplier
    ATTR_CONFLICT_RES = Use Requestor
    IGNORE_NULLS = No
    REJECT_NULL_MISSING_KEYS = No
    MERGED -> AttributeManager
AttributeManager
    ATTR_TABLE:
      REMOVE FACILITY_CODE
      REMOVE ROOM_NUMBER
      REMOVE FACILITY_NUMBER
      RENAME_SET_VALUE SPACEID > GS_OCC.SPACEID
      REMOVE ROOMNUMBER
      RENAME_SET_VALUE FLOORKEY > GS_OCC.FLOORKEY
      REMOVE BUILDINGKEY
    -> FeatureMerger_3 [SUPPLIER]
DBO.InteriorSpace (reader GEODATABASE_SDE_1)
    attributes: OBJECTID integer, SPACEID char(50), ROOMNUMBER char(25), ACCESSTYPEKEY char(50), ADA char(15), ALLOCATIONPCT double, ASSIGNMENTKEY char(50), CAPACITY integer, PHYSICALCAPACITY integer, CEILINGHEIGHT double, DESCRIPTION char(255), FLOORKEY char(50), FLOORCODE char(5), GROSSAREA double, LONGNAME char(100), NETAREA double, OCCUPANCY smallint, SECTIONKEY char(50), SHORTNAME char(25), SPACESTANDARDKEY char(50), SPACETYPECAT1KEY char(5), SPACETYPECAT2KEY char(5), SPACEUSECAT1KEY char(5), SPACEUSECAT2KEY char(5), AVAILABILITY char(50), USABLE char(10), ASSIGNABLE char(10), ORGASSIGNABLE char(10), VACANCY smallint, created_date date,
      created_user char(255), last_edited_date date, last_edited_user char(255), BUILDINGKEY char(50), ASSIGNMENTCOLLEGEKEY char(3), ASSIGNMENTDEPARTMENTKEY char(7), ASSIGNMENTSUBCOLLEGEKEY char(5), SHAPE.STArea() double, SHAPE.STLength() double
    -> AttributeManager_3
AttributeManager_3
    ATTR_TABLE:
      REMOVE OBJECTID
      RENAME_SET_VALUE SPACEID > MATCH_SPACEID
      REMOVE ROOMNUMBER
      REMOVE ACCESSTYPEKEY
      REMOVE ADA
      REMOVE ALLOCATIONPCT
      REMOVE ASSIGNMENTKEY
      REMOVE CAPACITY
      REMOVE PHYSICALCAPACITY
      REMOVE CEILINGHEIGHT
      REMOVE DESCRIPTION
      REMOVE FLOORCODE
      REMOVE GROSSAREA
      REMOVE LONGNAME
      REMOVE NETAREA
      REMOVE OCCUPANCY
      REMOVE SECTIONKEY
      REMOVE SHORTNAME
      REMOVE SPACESTANDARDKEY
      REMOVE SPACETYPECAT1KEY
      REMOVE SPACETYPECAT2KEY
      REMOVE SPACEUSECAT1KEY
      REMOVE SPACEUSECAT2KEY
      REMOVE AVAILABILITY
      REMOVE USABLE
      REMOVE ASSIGNABLE
      REMOVE ORGASSIGNABLE
      REMOVE VACANCY
      REMOVE created_date
      REMOVE created_user
      REMOVE last_edited_date
      REMOVE last_edited_user
      REMOVE BUILDINGKEY
      REMOVE ASSIGNMENTCOLLEGEKEY
      REMOVE ASSIGNMENTDEPARTMENTKEY
      REMOVE ASSIGNMENTSUBCOLLEGEKEY
      REMOVE SHAPE.STArea()
      REMOVE SHAPE.STLength()
    -> Debug_Tester_4
Debug_Tester_4: Tester
    TEST_CLAUSE = TEST $(debug) = F
    TEST_DESCRIPTION = ""
    BOOL_OP = OR
    TEST_MODE = Automatic
    PASSED -> SpatialRelator_2 [Supplier]
    FAILED -> Tester_6
Tester_6
    TEST_CLAUSE = TEST @Value(FLOORKEY) = $(testfloor)
    TEST_DESCRIPTION = ""
    BOOL_OP = AND
    TEST_MODE = Automatic
    PASSED -> SpatialRelator_2 [Supplier]
SpatialRelator_2
    SUCCESS_ATTR = _related_candidates
    GROUP_BY = FLOORKEY
    PREDICATES = INTERSECTS
    CURVE_BOUNDARY_RULE_PARAM = Default Rule
    AGGREGATE_HANDLING = Yes
    CALC_CARD = No
    LIST_NAME = _relationships
    -> Tester_8
Tester_8
    TEST_CLAUSE:
      TEST @Value(NonEmployee) = No
      TEST EMPLOYEEID NOT_ATTRIBUTE_VALUE_NULL ""
    TEST_DESCRIPTION = ""
    BOOL_OP = AND
    TEST_MODE = Automatic
    PASSED -> FeatureMerger_3 [REQUESTOR]
FeatureMerger_3
    PROCESS_DUPS = No
    MERGE_TYPE = Attributes Only
    JOIN_KEYS = @Value(SPACEKEY) @Value(GS_OCC.SPACEID) AUTO @Value(EMPLOYEEID) @Value(EMPLOYEEID) AUTO
    SUPPLIERS_FIRST = No
    ATTR_ACCUM_MODE = Merge Supplier
    ATTR_CONFLICT_RES = Use Requestor
    IGNORE_NULLS = No
    REJECT_NULL_MISSING_KEYS = No
    MERGED -> Tester_10
    NOT_MERGED -> DBO.RTW_PersonMarker (writer GEODATABASE_SDE_6)
    UNREFERENCED -> Tester_4

Bookmark: Original
DBO.RTW_PersonMarker (reader GEODATABASE_SDE_3)
    attributes: OBJECTID integer, created_user char(255), created_date date, last_edited_user char(255), last_edited_date date, FLOORKEY char(50), EMPLOYEEID char(9), SPACEKEY char(50), LocationMatchesGeoSIMS char(50), Distance double, NonEmployee char(255)
    -> AttributeRemover_6
AttributeRemover_6
    REMOVE_ATTRS = last_edited_date,last_edited_user,created_user,created_date
    -> Debug_Tester
Debug_Tester: Tester
    TEST_CLAUSE = TEST $(debug) = F
    TEST_DESCRIPTION = ""
    BOOL_OP = OR
    TEST_MODE = Automatic
    PASSED -> SpatialRelator_2 [Requestor]
    FAILED -> Tester_5
Tester_5
    TEST_CLAUSE = TEST @Value(FLOORKEY) = $(testfloor)
    TEST_DESCRIPTION = ""
    BOOL_OP = AND
    TEST_MODE = Automatic
    PASSED -> SpatialRelator_2 [Requestor]

Bookmark: Update
Tester_10
    TEST_CLAUSE:
      TEST @Value(SPACEKEY) = @Value(_relationships{0}.MATCH_SPACEID)
      TEST @Value(SPACEKEY) = @Value(GS_OCC.SPACEID)
    TEST_DESCRIPTION = ""
    BOOL_OP = AND
    TEST_MODE = Automatic
    PASSED -> AttributeCreator_4
    FAILED -> AttributeCreator_3
AttributeCreator_4
    ATTR_TABLE:
      SET_TO LocationMatchesGeoSIMS = Yes
      SET_TO SPACEKEY = @Value(MATCH_SPACEID)
    -> DBO.RTW_PersonMarker (writer GEODATABASE_SDE_5)
AttributeCreator_3
    ATTR_TABLE = SET_TO LocationMatchesGeoSIMS = No
    -> DBO.RTW_PersonMarker (writer GEODATABASE_SDE_5)
DBO.RTW_PersonMarker (writer GEODATABASE_SDE_5)
    attributes: OBJECTID integer, FLOORKEY integer, EMPLOYEEID char(9), SPACEKEY char(50), LocationMatchesGeoSIMS char(50), Distance double, NonEmployee char(255)

Bookmark: Delete
DBO.RTW_PersonMarker (writer GEODATABASE_SDE_6)
    attributes: OBJECTID integer, FLOORKEY integer, EMPLOYEEID char(9), SPACEKEY char(50), LocationMatchesGeoSIMS char(50), Distance double, NonEmployee char(255)

Bookmark: Add
Tester_4
    TEST_CLAUSE = TEST @Value(_occupant_count) NOT_= 1
    TEST_DESCRIPTION = ""
    BOOL_OP = OR
    TEST_MODE = Automatic
    PASSED -> Offsetter
    FAILED -> AttributeRenamer
Offsetter
    MODE = Polar Coordinate
    RADIUS_2D = 0.9144
    AZIMUTH_2D = 360/@Value(_occupant_count)*@Value(_element_index)
    OFFSET -> AttributeRenamer
AttributeRenamer
    ATTR_TABLE:
      RENAME_SET_DEFAULT OCCUPANT_EID > EMPLOYEEID
      RENAME_SET_DEFAULT SPACEID > SPACEKEY
    -> AttributeCreator_5
AttributeCreator_5
    ATTR_TABLE:
      SET_TO LocationMatchesGeoSIMS = Yes
      SET_TO SPACEKEY = @Value(GS_OCC.SPACEID)
      SET_TO Distance = 6
      SET_TO NonEmployee = No
      SET_TO FLOORKEY = @Value(GS_OCC.FLOORKEY)
    -> DBO.RTW_PersonMarker (writer GEODATABASE_SDE_4)
DBO.RTW_PersonMarker (writer GEODATABASE_SDE_4)
    attributes: FLOORKEY char(50), EMPLOYEEID char(9), SPACEKEY char(50), LocationMatchesGeoSIMS char(50), Distance double, NonEmployee char(255)
