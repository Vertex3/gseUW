FME workspace uw_Update_EvacCache_FloorPlans.fmw

Readers:
- GEODATABASE_SDE_1: GEODATABASE_SDE

Writers:
- GEODATABASE_SDE_2: GEODATABASE_SDE

DBO.Evac_MapLocations (reader GEODATABASE_SDE_1)
    attributes: OBJECTID integer, ModRotation range_domain(dEvac_ModRotation:double:0:360), FLOORKEY char(50), created_user char(255), created_date date, last_edited_user char(255), last_edited_date date
    -> FeatureMerger_2 [REQUESTOR]
DBO.Floor (reader GEODATABASE_SDE_1)
    attributes: OBJECTID integer, FLOORID char(50), FLOORCODE char(5), BUILDINGKEY char(50), BUILDINGNAME char(50), FLOORSHORTNAME char(50), FLOORLONGNAME char(100), GROSSAREA double, NETAREA double, USABLEAREA double, ASSIGNABLEAREA double, PERCENTUSABLE double, PERCENTASSIGNABLE double, ROTATION double, VERTORDER smallint, DDPFLOORSORT char(71), ROOF char(10), created_date date, created_user char(255), last_edited_date date, last_edited_user char(255), SHAPE.STArea() double, SHAPE.STLength() double
    -> FeatureMerger_2 [SUPPLIER]
FeatureMerger_2
    ATTR_CONFLICT_RES = Use Requestor
    JOIN_KEYS = @Value(FLOORKEY) @Value(FLOORID) AUTO
    MERGE_TYPE = Attributes Only
    ATTR_ACCUM_MODE = Merge Supplier
    IGNORE_NULLS = No
    PROCESS_DUPS = No
    REJECT_NULL_MISSING_KEYS = No
    SUPPLIERS_FIRST = No
    MERGED -> AttributeCreator_2
AttributeCreator_2
    ATTR_TABLE:
      SET_TO MapFloorID = @Value(FLOORKEY)_@Value(OBJECTID)
      SET_TO Rotation = @sum(@Value(ModRotation),@Value(ROTATION))
    -> FeatureMerger [SUPPLIER]
    -> FeatureMerger_3 [SUPPLIER]
    -> FeatureMerger_4 [SUPPLIER]

Bookmark: New Bookmark
DBO.InteriorSpace_ALL (reader GEODATABASE_SDE_1)
    attributes: OBJECTID integer, SPACEID char(50), ROOMNUMBER char(25), ACCESSTYPEKEY char(50), ADA char(15), ALLOCATIONPCT double, ASSIGNMENTKEY char(50), CAPACITY integer, PHYSICALCAPACITY integer, CEILINGHEIGHT double, DESCRIPTION char(255), FLOORKEY char(50), FLOORCODE char(5), GROSSAREA double, LONGNAME char(100), NETAREA double, OCCUPANCY smallint, SECTIONKEY char(50), SHORTNAME char(25), SPACESTANDARDKEY char(50), SPACETYPECAT1KEY char(5), SPACETYPECAT2KEY char(5), SPACEUSECAT1KEY char(5), SPACEUSECAT2KEY char(5), AVAILABILITY char(50), USABLE char(10), ASSIGNABLE char(10), ORGASSIGNABLE char(10), VACANCY smallint, created_date date,
      created_user char(255), last_edited_date date, last_edited_user char(255), BUILDINGKEY char(50), ASSIGNMENTCOLLEGEKEY char(3), ASSIGNMENTDEPARTMENTKEY char(7), ASSIGNMENTSUBCOLLEGEKEY char(5), SHAPE.STArea() double, SHAPE.STLength() double
    -> Tester
Tester
    TEST_CLAUSE:
      TEST @Value(SPACETYPECAT2KEY) = 010
      TEST @Value(ROOMNUMBER) CONTAINS EL
      TEST @Value(ROOMNUMBER) CONTAINS ST
    TEST_MODE = Automatic
    TEST_DESCRIPTION = ""
    BOOL_OP = OR
    PASSED -> FeatureMerger [REQUESTOR]
FeatureMerger
    ATTR_CONFLICT_RES = Use Requestor
    JOIN_KEYS = @Value(FLOORKEY) @Value(FLOORKEY) AUTO
    MERGE_TYPE = Attributes and Geometry
    ATTR_ACCUM_MODE = Merge Supplier
    CONNECT_Z_MODE = First Wins
    IGNORE_NULLS = No
    PROCESS_DUPS = Yes
    REJECT_NULL_MISSING_KEYS = No
    SUPPLIERS_FIRST = No
    GEOM_TYPE = Build Polygons
    LIST_NAME = _list
    MERGED -> ListExploder
ListExploder
    ATTR_CONFLICT_RES = Use Incoming List
    LIST_ATTR = _list{}
    INDEX_ATTR = _element_index
    ATTR_ACCUM_MODE = Merge Incoming List
    ELEMENTS -> AttributeRemover
AttributeRemover
    REMOVE_ATTRS = ADA,ASSIGNMENTDEPARTMENTKEY,ASSIGNABLE,ALLOCATIONPCT,ACCESSTYPEKEY,ASSIGNMENTSUBCOLLEGEKEY,ASSIGNABLEAREA,ASSIGNMENTCOLLEGEKEY,ASSIGNMENTKEY
    -> DBO.EvacCache_InteriorSpaces (writer GEODATABASE_SDE_2)
DBO.EvacCache_InteriorSpaces (writer GEODATABASE_SDE_2)
    attributes: MapFloorID char(50), ROOMNUMBER char(25), SPACETYPECAT1KEY char(5), SPACETYPECAT2KEY char(5), Rotation double

Bookmark: New Bookmark
DBO.FloorplanLine_ALL (reader GEODATABASE_SDE_1)
    attributes: OBJECTID integer, BUILDINGKEY char(50), FLOORKEY char(50), FLOORCODE char(5), LINETYPE char(50), created_user char(255), created_date date, last_edited_user char(255), last_edited_date date, SHAPE.STLength() double
    -> FeatureMerger_3 [REQUESTOR]
FeatureMerger_3
    ATTR_CONFLICT_RES = Use Requestor
    JOIN_KEYS = @Value(FLOORKEY) @Value(FLOORKEY) AUTO
    MERGE_TYPE = Attributes and Geometry
    ATTR_ACCUM_MODE = Merge Supplier
    CONNECT_Z_MODE = First Wins
    IGNORE_NULLS = No
    PROCESS_DUPS = Yes
    REJECT_NULL_MISSING_KEYS = No
    SUPPLIERS_FIRST = No
    GEOM_TYPE = Build Polygons
    LIST_NAME = _list
    MERGED -> ListExploder_2
ListExploder_2
    ATTR_CONFLICT_RES = Use Incoming List
    LIST_ATTR = _list{}
    INDEX_ATTR = _element_index
    ATTR_ACCUM_MODE = Merge Incoming List
    ELEMENTS -> DBO.EvacCache_FloorPlaneLines (writer GEODATABASE_SDE_2)
DBO.EvacCache_FloorPlaneLines (writer GEODATABASE_SDE_2)
    attributes: OBJECTID integer, LINETYPE char(50), MapFloorID char(50), SHAPE.STLength() double

Bookmark: New Bookmark
DBO.FloorArea_ALL (reader GEODATABASE_SDE_1)
    attributes: OBJECTID integer, BUILDINGKEY char(50), FLOORID char(50), FLOORCODE char(5), FLOORAREA double, SOURCEDWG char(60), LASTUPDATE date, LASTEDITOR char(30), SHAPE.STArea() double, SHAPE.STLength() double
    -> FeatureMerger_4 [REQUESTOR]
FeatureMerger_4
    ATTR_CONFLICT_RES = Use Requestor
    JOIN_KEYS = @Value(FLOORID) @Value(FLOORKEY) AUTO
    MERGE_TYPE = Attributes and Geometry
    ATTR_ACCUM_MODE = Merge Supplier
    CONNECT_Z_MODE = First Wins
    IGNORE_NULLS = No
    PROCESS_DUPS = Yes
    REJECT_NULL_MISSING_KEYS = No
    SUPPLIERS_FIRST = No
    GEOM_TYPE = Build Polygons
    LIST_NAME = _list
    MERGED -> ListExploder_3
ListExploder_3
    ATTR_CONFLICT_RES = Use Incoming List
    LIST_ATTR = _list{}
    INDEX_ATTR = _element_index
    ATTR_ACCUM_MODE = Merge Incoming List
    ELEMENTS -> DBO.EvacCache_FloorArea (writer GEODATABASE_SDE_2)
DBO.EvacCache_FloorArea (writer GEODATABASE_SDE_2)
    attributes: OBJECTID integer, MapFloorID char(50), SHAPE.STArea() double, SHAPE.STLength() double
