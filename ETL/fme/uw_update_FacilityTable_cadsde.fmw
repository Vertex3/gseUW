FME workspace uw_update_FacilityTable_cadsde.fmw

Readers:
- GEODATABASE_SDE_1: GEODATABASE_SDE

Writers:
- GEODATABASE_SDE_2: GEODATABASE_SDE

dbo.FACILITY_TABLE (reader GEODATABASE_SDE_1)
    attributes: FACILITY_CODE char(4), FACILITY_TYPE char(4), STATUS char(3), NAME char(20), LONG_NAME char(100), SITE char(7), YEAR_CONSTRUCTED char(4), SECTOR char(3), REGISTERED_HISTORIC_SITE char(1), LAST_MAJOR_RENOVATION_DATE date, CONSTRUCTION_TYPE char(5), WEB_PLAN char(1), OFM_CITY_CODE char(4), OFM_COUNTY_CODE char(3), OFM_LEASE_START_DATE date, OFM_LEASE_END_DATE date, OFM_SITE_CODE char(3), OFM_LEGISLATIVE_DISTRICT char(2), OFM_CONDITION char(1), OFM_SITE_ADDRESS char(40), OFM_HSR char(3), BUILDING char(3), CENTER_FACILITY_LATITUDE double, CENTER_FACILITY_LONGITUDE double, MOD_USER char(30), MOD_DATE date, OS_USER char(30), CREATE_USER char(30), CREATE_DATE date, LEASED_OR_OWNED char(6),
      FACILITY_NUMBER smallint, GROSS_SQUARE_FEET integer, CONSTRUCTION_OR_PURCHASE_COST integer, LAST_MAJOR_RENOVATION_COST integer, AGGREGATE_FACILITY_NUMBER smallint, OFM_REPLACEMENT_COST_FACTOR integer
    -> dbo.FACILITY_TABLE (writer GEODATABASE_SDE_2)
dbo.FACILITY_TABLE (writer GEODATABASE_SDE_2)
    attributes: FACILITY_CODE char(4), FACILITY_TYPE char(4), STATUS char(3), NAME char(20), LONG_NAME char(100), SITE char(7), YEAR_CONSTRUCTED char(4), SECTOR char(3), REGISTERED_HISTORIC_SITE char(1), LAST_MAJOR_RENOVATION_DATE date, CONSTRUCTION_TYPE char(5), WEB_PLAN char(1), OFM_CITY_CODE char(4), OFM_COUNTY_CODE char(3), OFM_LEASE_START_DATE date, OFM_LEASE_END_DATE date, OFM_SITE_CODE char(3), OFM_LEGISLATIVE_DISTRICT char(2), OFM_CONDITION char(1), OFM_SITE_ADDRESS char(40), OFM_HSR char(3), BUILDING char(3), CENTER_FACILITY_LATITUDE double, CENTER_FACILITY_LONGITUDE double, MOD_USER char(30), MOD_DATE date, OS_USER char(30), CREATE_USER char(30), CREATE_DATE date, LEASED_OR_OWNED char(6),
      FACILITY_NUMBER smallint, GROSS_SQUARE_FEET integer, CONSTRUCTION_OR_PURCHASE_COST integer, LAST_MAJOR_RENOVATION_COST integer, AGGREGATE_FACILITY_NUMBER smallint, OFM_REPLACEMENT_COST_FACTOR integer
