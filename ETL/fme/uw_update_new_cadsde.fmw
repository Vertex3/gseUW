FME workspace uw_update_new_cadsde.fmw

Parameters:
- FEATURE_TYPES = DBO.DrawingType_Outline DBO.DrawingType_RT DBO.DrawingType_XP dbo.FACILITY_TABLE DBO.Floor_Level DBO.Floor_Poly DBO.Floor_Table DBO.FloorArea DBO.FloorArea_Isometric DBO.FloorPageTemplate DBO.FloorplanLine DBO.FloorplanLine_Isometric DBO.gzError DBO.gzLog DBO.InteriorSpace DBO.InteriorSpace_Isometric DBO.InteriorSpace_Point DBO.PDF_ErrorRemoval DBO.PDF_Errors DBO.PDF_ExportLog DBO.PDF_LogBuildings DBO.PDF_LogBuildings_Test DBO.PDF_LogFloors DBO.PDF_LogFloors_Test DBO.PDF_zErrors DBO.Building_Table

Readers:
- GEODATABASE_SDE_1: GEODATABASE_SDE

Writers:
- GEODATABASE_SDE_2: GEODATABASE_SDE
- GEODATABASE_SDE_3: GEODATABASE_SDE
- GEODATABASE_SDE_4: GEODATABASE_SDE

DBO.PDF_zErrors (reader GEODATABASE_SDE_1)
    attributes: OBJECTID integer, ErrorType char(50), UniqueID char(60), Date date, GROUNDOFFSET double, FloorID char(60), FACILITY_TYPE char(4), NAME char(20), ACTIVEFLAG char(255), FilePath char(255), YEAR_CONSTRUCTED char(4), ROOMNUMBER char(30), OFM_LEASE_START_DATE date, LAST_MAJOR_RENOVATION_COST integer, BUILDING char(3), OFM_CITY_CODE char(4), SHAPE.STLength() double, AGGREGATE_FACILITY_NUMBER smallint, SITE char(7), REASON char(255), LOADTIME date, OFM_CONDITION char(1), MOD_DATE date, STATUS char(3), OS_USER char(30), SECTOR char(3), NAMELONG char(100), INTERIORSPACE char(3), REGISTERED_HISTORIC_SITE char(1), COMPLETED smallint,
      OFM_HSR char(3), FACILITY_NUMBER smallint, FACILITY_CODE char(4), FLOORCODE char(20), GROSS_SQUARE_FEET integer, FLOORPLANLINE char(3), LEASED_OR_OWNED char(6), FLOORPAGETEMPLATE char(3), SPACEAREA double, OFM_SITE_ADDRESS char(40), CENTER_FACILITY_LATITUDE double, SOURCEDWG char(60), PROCNAME char(255), LAST_MAJOR_RENOVATION_DATE date, MOD_USER char(30), BuildingID char(60), FLOORAREA double, OFM_LEGISLATIVE_DISTRICT char(2), CREATE_DATE date, SPACEID char(60), LOADNAME char(255), OFM_LEASE_END_DATE date, DATASET char(255), LOADUSER char(255), LOCALROT double, HASROUTE char(3), OFM_COUNTY_CODE char(3), SOURCEID char(30), SITEID char(60), ROOFOUTLINE char(3),
      DRAWINGNAME char(100), BASEMAPOUTLINE char(3), SPACECLASS char(60), SCHELEV integer, OFM_REPLACEMENT_COST_FACTOR integer, BUILDINGID char(60), SRCIDFIELD char(255), FLOORID char(60), CONSTRUCTION_TYPE char(5), FLOORLEVEL integer, PrintType char(50), CREATE_USER char(30), LONG_NAME char(100), WEB_PLAN char(1), CENTER_FACILITY_LONGITUDE double, SRCIDVAL char(255), LASTEDITOR char(30), ERRTIME date, LASTUPDATE date, ERRUSER char(255), NAMESHORT char(50), SOURCELAYER char(24), CONSTRUCTION_OR_PURCHASE_COST integer, SHAPE.STArea() double, CALCROT double, SOURCENAME char(255), OFM_SITE_CODE char(3), PrintTemplate char(60)
    -> DYNAMIC (writer GEODATABASE_SDE_2)
    -> FeatureClass1 (writer GEODATABASE_SDE_3)
    -> FeatureClass1 (writer GEODATABASE_SDE_4)

Bookmark: old cadsde
DYNAMIC (writer GEODATABASE_SDE_2)

Bookmark: Test
FeatureClass1 (writer GEODATABASE_SDE_3)

Bookmark: Dev
FeatureClass1 (writer GEODATABASE_SDE_4)
