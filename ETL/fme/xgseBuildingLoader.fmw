FME workspace xgseBuildingLoader.fmw
Title: GizintaLoader
Description: First Beta release of Gizinta for FME
Usage: Add the xml file and other parameters
Requirements: test
History: 31/10/2013,support@Gizinta.com,First Draft
Legal terms conditions: This work is licensed under the Creative Commons Attribution-ShareAlike 3.0 Unported License.
Startup Python:
      import xml.dom.minidom
      import os
      import sys
      import time
      import fmeobjects

      ospath = FME_MacroValues['FME_MF_DIR']
      print ospath
      if ospath not in sys.path:
          sys.path.append(ospath)
      import gzfme

      ErrorUniqueID = "ErrorUniqueID"
      ErrorRequiredValue = "ErrorRequiredValue"
      ErrorValueMap = "ErrorValueMap"
      Errors = False

      debug = gzfme.setDebug(FME_MacroValues['gzDebug'])
      logger = fmeobjects.FMELogFile()
      gzfme.logger = logger
Shutdown Python:
      import fmeobjects, gzfme

      gzfme.shutdown(Errors,str(FME_MacroValues['IgnoreErrors']),FME_TotalFeaturesWritten,FME_MacroValues)

      del Errors
      del ErrorUniqueID
      del ErrorRequiredValue
      del ErrorValueMap
      del debug
      del logger
      gzfme.logger = None

Parameters:
- DestDataset_GEODATABASE_SDE = sde   # Destination Esri ArcSDE Geodatabase Dataset
- OUT_CONNECTION_FILE_GEODATABASE_SDE = C:\Apps\Gizinta\gseUW\ETL\serverConfig\GIS Staging.sde   # Connection File
- GizintaProject = C:\Apps\Gizinta\gseUW\ETL\config\bldgLoadPlaylist.xml   # Select the Gizinta Xml File to use
- SourceFieldQA = False   # Choose whether to perform QA on Source Fields
- TargetFieldQA = True   # Choose whether to perform QA on Target Fields
- IgnoreErrors = False   # Ignore Errors and continue
- SourceDatasetTypes = CADDataset   # Enter the Gizinta Source Dataset Type
- gzDebug = False   # Enable gzDebug (True/False)
- LOG_FILE =   # Log File
- SourceCoordinateSystem = EPSG:2285   # Source Coordinate System
- SourceDataset_ESRIMSD = C:\Apps\Gizinta\CADVault\Floorplans\**\*Outline.dwg   # Source Autodesk AutoCAD DWG/DXF File(s)
- FEATURE_TYPES_READ = Building_Footprint Building_Roof Building_Outline_Tilt   # Feature Types to Read
- SourceDataset_GEODATABASE_SDE = sde   # Source Esri ArcSDE Geodatabase Dataset
- FEATURE_TYPES =   # DBO.FloorPageTemplate Feature Types to Read

Readers:
- ESRIMSD_1: ESRIMSD from $(SourceDataset_ESRIMSD)
- GEODATABASE_SDE_1: GEODATABASE_SDE from $(SourceDataset_GEODATABASE_SDE)

Writers:
- GEODATABASE_SDE_2: GEODATABASE_SDE to $(DestDataset_GEODATABASE_SDE)

Building_Roof (reader ESRIMSD_1)
    attributes: FACNUM char(254)
    -> AttributeExposer
AttributeExposer
    ATTR_LIST = fme_basename,fme_feature_type,FACNUM,autocad_source_filename
    -> Tester
Tester
    TEST_DESCRIPTION = ""
    TEST_MODE = Automatic
    TEST_CLAUSE = TEST $(FEATURE_TYPES_READ) CONTAINS @Value(fme_feature_type)
    BOOL_OP = OR
    PASSED -> Reprojector_2
Reprojector_2
    STROKE_ARCS = Yes
    DEST = EPSG:3857
    RASTER_CELL_SIZE = Preserve Cells
    INTERPOLATION_TYPE_NAME = Nearest Neighbor
    SOURCE = $(SourceCoordinateSystem)
    REPROJECTED -> gzFieldCalculator
gzFieldCalculator
    AddFieldsValues_Output_1 -> Reprojector
Reprojector
    STROKE_ARCS = Yes
    DEST = EPSG:3857
    RASTER_CELL_SIZE = Preserve Cells
    INTERPOLATION_TYPE_NAME = Nearest Neighbor
    SOURCE = $(SourceCoordinateSystem)
    REPROJECTED -> TestFilter_2
TestFilter_2
    TEST_LIST = BOOL_OP,OR,COMPOSITE_TEST,<Unused>,TEST_CLAUSE,"TEST @Value(fme_feature_type) = FloorPageTemplate",FloorPageTemplate
    DEFAULT_VALUE = <UNFILTERED>
    FloorPageTemplate -> bldg
bldg: AttributeExposer
    ATTR_LIST = BUILDINGID
    -> AttributeCreator_2
Note: Special Calculations for Outline attributes
AttributeCreator_2
    ATTR_LIST = fme_feature_type,FloorPageTemplate
    -> gzBuildingOutlineTilt
gzBuildingOutlineTilt
    BUILDINGID = @Value(BUILDINGID)
    -> gzSourceTargetQA
gzSourceTargetQA
    SourceTargetQA_Output_1 -> gzWriteData
gzWriteData
    GroupBy = @Value(BUILDINGID)
    HASERRORS = @Value(HasErrors)
    IgnoreErrors = False
    gzLogWriter -> gzLog (writer GEODATABASE_SDE_2)
    gzErrorWriter -> gzError (writer GEODATABASE_SDE_2)
    gzFeatureWriter -> DBO.Building_Outline_Tilt (writer GEODATABASE_SDE_2)
gzLog (writer GEODATABASE_SDE_2)
    attributes: PROCNAME char(255), LOADTIME date, LOADNAME char(255), DATASET char(255), COMPLETED smallint, LOADUSER char(255), ACTIVEFLAG char(255)
DBO.Building_Outline_Tilt (writer GEODATABASE_SDE_2)
    attributes: geodb_oid integer, OBJECTID integer, SITEID char(60), BUILDINGID char(60), CALCROT double, SOURCEID char(30), SOURCEDWG char(60), LASTUPDATE date, LASTEDITOR char(30), BLDGNAME char(100), SHAPE.STArea() double, SHAPE.STLength() double
gzError (writer GEODATABASE_SDE_2)
    attributes: PROCNAME char(255), SOURCENAME char(255), SRCIDFIELD char(255), SRCIDVAL char(255), DATASET char(255), REASON char(255), ERRUSER char(255), ERRTIME date, ACTIVEFLAG char(255)
CenterPointReplacer
    CENTERPOINT -> AttributeCreator
Note: no longer used. Building Points from siteplan
AttributeCreator
    ATTR_LIST = fme_feature_type,Building_Outline_Point

FME custom transformer gzTiltRooms
Tilt Rooms in floorplans to create a pseudo-isometric view of the rooms and floors

Parameters:
- pFACNUM =   # Enter the Building Identifier
- pFacFloor =   # Enter the FacFloor Number

INPUT (input)
    -> DuplicateRemover
    -> FeatureMerger_2 [input 1]
    -> DuplicateRemover_2
DuplicateRemover_2
    KEYATTR = $(pFACNUM)
    UNIQUE -> BldgReader
BldgReader: FeatureReader
    GEODATABASE_SDE_REMOVE_TABLE_QUALIFIER = NO
    DATASET = sde
    FORMAT = GEODATABASE_SDE
    ATTRIBUTES = DBO.Building_Outline,"geodb_oid,OBJECTID,FACNUM,HULLROT,BLDGHEIGHT,MODANGLE,SPACING,MARGIN,XCENTER,YCENTER,SHAPE.STArea(),SHAPE.STLength()"
    GEODATABASE_SDE_RESOLVE_SUBTYPE_NAMES = yes
    GEODATABASE_SDE_VERSION_TYPE = Connect using a Transactional Version
    GEODATABASE_SDE_SPLIT_COMPLEX_EDGES = no
    COMBINE_GEOM = Keep result geometry only
    GEODATABASE_SDE_TRANSLATE_SPATIAL_DATA_ONLY = no
    FEATURETYPES = DBO.Building_Outline
    GEODATABASE_SDE_WHERE = FACNUM=@Value(FACNUM)
    GEODATABASE_SDE_CONNECTION_FILE = $(FME_MF_DIR)GIS Production.sde
    COMBINE_ATTRS = Keep result attributes only
    GEODATABASE_SDE_IGNORE_RELATIONSHIP_INFO = yes
    GEODATABASE_SDE_VERSION = SDE.DEFAULT
    SUPPORTED_SPATIAL_INTERACTIONS = ENVELOPE_INTERSECT%ENVELOPE_INTERSECT%INTERSECTS%CONTAINS%CROSSES%DISJOINT%EQUALS%OVERLAPS%TOUCHES%WITHIN
    GEODATABASE_SDE_TABLELIST = DBO.Building_Outline
    GEODATABASE_SDE_SPLIT_MULTI_PART_ANNOS = no
    GEODATABASE_SDE_IGNORE_NETWORK_INFO = yes
    GEODATABASE_SDE_CONNECTION = Connection File
    GEODATABASE_SDE_RESOLVE_DOMAINS = no
    DBO.Building_Outline -> BoundsExtractor_2
BoundsExtractor_2
    ZMIN = _zmin
    ZMAX = _zmax
    XMIN = _xmin
    XMAX = _xmax
    YMIN = _ymin
    YMAX = _ymax
    -> FeatureMerger_2 [input 2]
FeatureMerger_2
    PROCESS_DUPS = No
    SUPPLIER_PREFIX_DUMMY = YES
    IGNORE_NULLS = Yes
    SUPPLIERS_FIRST = No
    MERGE_TYPE = Attributes Only
    JOIN_KEYS = @Value(FACNUM) @Value(FACNUM)
    MERGED -> FeatureMerger_3 [input 1]
DuplicateRemover
    KEYATTR = $(pFACNUM)
    UNIQUE -> FloorsReader
FloorsReader: FeatureReader
    GEODATABASE_SDE_REMOVE_TABLE_QUALIFIER = NO
    DATASET = sde
    FORMAT = GEODATABASE_SDE
    ATTRIBUTES = DBO.Active_Floor,"geodb_oid,OBJECTID,FACNUM,FLOOR,FACFLOOR,DWG_NAME,INTERIORSPACE,FLOORPLANLINE,SCHELEV,ALTITUDE,GlobalID"
    GEODATABASE_SDE_RESOLVE_SUBTYPE_NAMES = yes
    GEODATABASE_SDE_VERSION_TYPE = Connect using a Transactional Version
    GEODATABASE_SDE_SPLIT_COMPLEX_EDGES = no
    COMBINE_GEOM = In case of conflict, keep aggregate of INITIATOR and result geometry
    GEODATABASE_SDE_TRANSLATE_SPATIAL_DATA_ONLY = no
    FEATURETYPES = DBO.Active_Floor
    GEODATABASE_SDE_CONNECTION_FILE = $(FME_MF_DIR)GIS Production.sde
    COMBINE_ATTRS = In case of conflict, keep result attributes
    GEODATABASE_SDE_IGNORE_RELATIONSHIP_INFO = yes
    GEODATABASE_SDE_VERSION = SDE.DEFAULT
    SUPPORTED_SPATIAL_INTERACTIONS = ENVELOPE_INTERSECT%INTERSECTS%CONTAINS%CROSSES%DISJOINT%EQUALS%OVERLAPS%TOUCHES%WITHIN
    GEODATABASE_SDE_TABLELIST = DBO.Active_Floor
    GEODATABASE_SDE_SPLIT_MULTI_PART_ANNOS = no
    GEODATABASE_SDE_IGNORE_NETWORK_INFO = yes
    GEODATABASE_SDE_CONNECTION = Connection File
    GEODATABASE_SDE_RESOLVE_DOMAINS = no
    DBO.Active_Floor -> AttributeCopier_3
AttributeCopier_3
    ATTR_LIST = STACKLEVEL,SCHELEV
    -> FeatureMerger_3 [input 2]
FeatureMerger_3
    PROCESS_DUPS = No
    SUPPLIER_PREFIX_DUMMY = YES
    IGNORE_NULLS = Yes
    SUPPLIERS_FIRST = No
    MERGE_TYPE = Attributes Only
    JOIN_KEYS = @Value(FACFLOOR) @Value(FACFLOOR)
    MERGED -> ExpressionEvaluator_2
ExpressionEvaluator_2
    EXPRESSION = @Value(MODANGLE) + @Value(HULLROT) + 15.0
    VAL_ATTR = CALCULATED_ROTATION
    -> Rotator
Rotator
    YORIG = 0
    XORIG = 0
    ANGLE = @Value(CALCULATED_ROTATION)
    ROTATED -> Y_Base
Y_Base: ExpressionEvaluator
    EXPRESSION = @Value(_ymin) + (@Value(SPACING) * @Value(STACKLEVEL))
    VAL_ATTR = _yBase
    -> tilt_Space
tilt_Space: ExpressionEvaluator
    EXPRESSION = @Value(BLDGHEIGHT) / (@Value(SPACING)+0.00001)
    VAL_ATTR = _tiltSpace
    -> Chopper
Chopper
    MAX = 1
    CHOPPED -> CoordinateExtractor
CoordinateExtractor
    X_ATTR = _x
    Z_DEFAULT = -9999
    IND = 0
    Z_ATTR = _z
    Y_ATTR = _y
    -> tilt_y
tilt_y: ExpressionEvaluator
    EXPRESSION = @Value(_yBase) + ((@Value(_y) - @Value(_ymin)) / @Value(_tiltSpace)) * (1 - @Value(MARGIN))
    VAL_ATTR = _tiltY
    -> 2DPointReplacer
2DPointReplacer
    XVALATTR = @Value(_x)
    YVALATTR = @Value(_tiltY)
    POINT -> PointConnector
PointConnector
    BREAKATTR = FACROOM
    POLYGON -> GeometryCoercer_2
    LINE -> GeometryCoercer_2
GeometryCoercer_2
    KIND = fme_polygon
    CHECKZ = No
    COERCED -> SliverRemover_2
SliverRemover_2
    REPAIR_METHOD = Longest Boundary
    REPAIRED -> SelfIntersectChecker_4
SelfIntersectChecker_4
    NotSelfIntersecting -> OUTPUT (output)
OUTPUT (output)

FME custom transformer gzCalculateRotation

Parameters:
- SourceCoordinateSystem = EPSG:2285   # Source Coordinate System

INPUT (input)
    -> AttributeCreator_7
AttributeCreator_7
    ATTR_LIST = WORLD,World
    -> AttributeFilter
AttributeFilter
    ATTR_NAME = text_line_number
    ATTR_VALUES = <BLANK>,<UNFILTERED>,1,2
    2 -> AttributeSplitter2
    1 -> AttributeSplitter1
AttributeSplitter1
    ATTR_NAME = text_line_data
    DELIMITER = " "
    DROP_EMPTY_PARTS = No
    TRIM_OPTION = None
    LIST_NAME = _pts
    -> AttributeSplitter_1
    -> AttributeSplitter_2
AttributeSplitter_1
    ATTR_NAME = _pts{0}
    DELIMITER = ,
    DROP_EMPTY_PARTS = No
    TRIM_OPTION = Both
    LIST_NAME = _pt
    -> AttributeCreator_1
AttributeCreator_1
    ATTR_LIST = x1,@Value(_pt{0}),y1,@Value(_pt{1})
    -> 2DPointAdder_1
2DPointAdder_1
    XVALATTR = @Value(x1)
    YVALATTR = @Value(y1)
    -> PointConnector
AttributeSplitter_2
    ATTR_NAME = _pts{1}
    DELIMITER = ,
    DROP_EMPTY_PARTS = No
    TRIM_OPTION = Both
    LIST_NAME = _pt2
    -> AttributeCreator_2
AttributeCreator_2
    ATTR_LIST = x2,@Value(_pt2{0}),y2,@Value(_pt2{1})
    -> 2DPointAdder_2
2DPointAdder_2
    XVALATTR = @Value(x2)
    YVALATTR = @Value(y2)
    -> PointConnector_2
AttributeSplitter2
    ATTR_NAME = text_line_data
    DELIMITER = " "
    DROP_EMPTY_PARTS = No
    TRIM_OPTION = None
    LIST_NAME = _pts
    -> AttributeSplitter_4
    -> AttributeSplitter_3
AttributeSplitter_3
    ATTR_NAME = _pts{0}
    DELIMITER = ,
    DROP_EMPTY_PARTS = No
    TRIM_OPTION = Both
    LIST_NAME = _pt
    -> AttributeCreator_3
AttributeCreator_3
    ATTR_LIST = x3,@Value(_pt{0}),y3,@Value(_pt{1})
    -> 2DPointAdder_3
2DPointAdder_3
    XVALATTR = @Value(x3)
    YVALATTR = @Value(y3)
    -> PointConnector
PointConnector
    LINE -> CoordinateExtractor
    LINE -> PointConnector_LINE
PointConnector_LINE: Inspector
CoordinateExtractor
    X_ATTR = _x1
    Z_DEFAULT = -9999
    IND = 0
    Z_ATTR = _z
    Y_ATTR = _y1
    -> CoordinateExtractor_2
CoordinateExtractor_2
    X_ATTR = _x2
    Z_DEFAULT = -9999
    IND = 1
    Z_ATTR = _z
    Y_ATTR = _y2
    -> ExpressionEvaluator1
ExpressionEvaluator1
    EXPRESSION = (@atan2((@Value(_y2)-@Value(_y1)),(@Value(_x2)-@Value(_x1))))*180.0/(22/7.0)
    VAL_ATTR = rot1
    -> FeatureMerger_3 [input 1]
AttributeSplitter_4
    ATTR_NAME = _pts{1}
    DELIMITER = ,
    DROP_EMPTY_PARTS = No
    TRIM_OPTION = Both
    LIST_NAME = _pt2
    -> AttributeCreator_4
AttributeCreator_4
    ATTR_LIST = x4,@Value(_pt2{0}),y4,@Value(_pt2{1})
    -> 2DPointAdder_4
2DPointAdder_4
    XVALATTR = @Value(x4)
    YVALATTR = @Value(y4)
    -> PointConnector_2
PointConnector_2
    LINE -> Reprojector_2
    LINE -> PointConnector_2_LINE
Reprojector_2
    STROKE_ARCS = Yes
    DEST = EPSG:3857
    RASTER_CELL_SIZE = Preserve Cells
    INTERPOLATION_TYPE_NAME = Nearest Neighbor
    SOURCE = $(SourceCoordinateSystem)
    REPROJECTED -> CoordinateExtractor_3
CoordinateExtractor_3
    X_ATTR = _x1
    Z_DEFAULT = -9999
    IND = 0
    Z_ATTR = _z
    Y_ATTR = _y1
    -> CoordinateExtractor_4
CoordinateExtractor_4
    X_ATTR = _x2
    Z_DEFAULT = -9999
    IND = 1
    Z_ATTR = _z
    Y_ATTR = _y2
    -> ExpressionEvaluator2
ExpressionEvaluator2
    EXPRESSION = (@atan2((@Value(_y2)-@Value(_y1)),(@Value(_x2)-@Value(_x1))))*180.0/(22/7.0)
    VAL_ATTR = rot2
    -> FeatureMerger_3 [input 2]
FeatureMerger_3
    PROCESS_DUPS = No
    SUPPLIER_PREFIX_DUMMY = YES
    IGNORE_NULLS = Yes
    SUPPLIERS_FIRST = No
    MERGE_TYPE = Attributes Only
    JOIN_KEYS = @Value(WORLD) @Value(WORLD)
    MERGED -> AttributeCreator
AttributeCreator
    ATTR_LIST = CALCROT,@Evaluate(@Value(rot2)-@Value(rot1)),WORLDFILE,@Value(text_line_data)
    -> ExpressionEvaluator_8
ExpressionEvaluator_8
    EXPRESSION = @Value(CALCROT) + 90.0
    VAL_ATTR = _angle
    -> TestFilter_5
TestFilter_5
    TEST_LIST = BOOL_OP,OR,COMPOSITE_TEST,<Unused>,TEST_CLAUSE,"TEST ""@Value(CALCROT)"" > ""180.0""",_angle > 180.0
    DEFAULT_VALUE = <UNFILTERED>
    _angle > 180.0 -> ExpressionEvaluator_10
    <UNFILTERED> -> AttributeRemover
ExpressionEvaluator_10
    EXPRESSION = @Value(CALCROT) -180.0
    VAL_ATTR = _angle
    -> AttributeRemover
AttributeRemover
    REMOVE_ATTRS = text_line_data,x1,y1,x2,y2,x3,y3,x4,y4,rot1,rot2,_list{0},_pt{0},_pt2{0},_list{1},_pt{1},_pt2{1}
    -> OUTPUT (output)
    -> AttributeCreator_OUTPUT
OUTPUT (output)
AttributeCreator_OUTPUT: Inspector
PointConnector_2_LINE: Inspector
Reprojector
    STROKE_ARCS = Yes
    DEST = EPSG:3857
    RASTER_CELL_SIZE = Preserve Cells
    INTERPOLATION_TYPE_NAME = Nearest Neighbor
    SOURCE = $(SourceCoordinateSystem)

FME custom transformer SelfIntersectChecker
Separates self-intersecting features from the rest of input. This custom transformer does not change the geometry of self-intersecting features. If you want to remove self-intersections, try the " SelfIntersector " transformer.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Input (input)
    -> PartCounter
PartCounter
    RECURSIVE_PARAM = No
    COUNT_ATTR = _part_count1
    -> COUNTER
COUNTER: Counter
    CNT_ATTR = _selfID
    DOMAIN = counter
    SCOPE = Local
    START = 0
    -> GeometryExtractor
GeometryExtractor
    KIND_LONG = OGC Well Known Text
    OGCVERSION = 1.2
    ATTR = _geometry
    -> SelfIntersector
SelfIntersector
    SEG_ATTR = _segments
    SELF_INTERSECTED -> DuplicateRemover
DuplicateRemover
    KEYATTR = _selfID
    UNIQUE -> TESTER
TESTER: Tester
    TEST_LIST = &_segments,>,1
    TEST_MODE = NUMERIC
    TEST_CLAUSE = TEST @Value(_segments) > 1
    BOOL_OP = OR
    FAILED -> PartCounter_2
    PASSED -> GeometryReplacer
PartCounter_2
    RECURSIVE_PARAM = No
    COUNT_ATTR = _part_count2
    -> TESTER_2
TESTER_2: Tester
    TEST_LIST = &_part_count1,=,&_part_count2
    TEST_MODE = Automatic
    TEST_CLAUSE = TEST @Value(_part_count1) = @Value(_part_count2)
    BOOL_OP = OR
    PASSED -> ATTRIBUTEREMOVER
    FAILED -> GeometryReplacer
ATTRIBUTEREMOVER: AttributeRemover
    REMOVE_ATTRS = _selfID,_geometry,_segments
    -> NotSelfIntersecting (output)
NotSelfIntersecting (output)
GeometryReplacer
    KIND_LONG = OGC Well Known Text
    ATTR = _geometry
    -> ATTRIBUTEREMOVER_2
ATTRIBUTEREMOVER_2: AttributeRemover
    REMOVE_ATTRS = _selfID,_geometry,_segments
    -> SelfIntersecting (output)
SelfIntersecting (output)

FME custom transformer gzBuildingOutline

Parameters:
- BUILDINGID = @Value(BUILDINGID)

INPUT (input)
    -> Chopper_2
    -> FeatureMerger_3 [input 1]
Chopper_2
    MAX = 2
    CHOPPED -> LengthCalculator_2
LengthCalculator_2
    DIM = 2
    MULT = 1
    LEN_ATTR = _length
    -> StatisticsCalculator_2
StatisticsCalculator_2
    STATS_ATTR = _length
    STDEV_ATTR = _stdev
    PASS_THROUGH = Yes
    MEDIAN_ATTR = _median
    NUMERIC_ATTR = _numeric_count
    MIN_ATTR = _min
    MAX_ATTR = _max
    MEAN_ATTR = _mean
    MODE_ATTR = _mode
    RANGE_ATTR = _range
    COUNT_ATTR = _count
    SUM_ATTR = _sum
    GROUP_BY = BUILDINGID
    STATISTICS -> TestFilter_6
TestFilter_6
    TEST_LIST = BOOL_OP,OR,COMPOSITE_TEST,<Unused>,TEST_CLAUSE,"TEST ""@Value(_length)"" = ""@Value(_max)""",_length = _max
    DEFAULT_VALUE = <UNFILTERED>
    _length = _max -> CoordinateExtractor_4
CoordinateExtractor_4
    X_ATTR = _x1
    Z_DEFAULT = -9999
    IND = 0
    Z_ATTR = _z
    Y_ATTR = _y1
    -> CoordinateExtractor_6
CoordinateExtractor_6
    X_ATTR = _x2
    Z_DEFAULT = -9999
    IND = 1
    Z_ATTR = _z
    Y_ATTR = _y2
    -> TestFilter_4
TestFilter_4
    TEST_LIST = BOOL_OP,OR,COMPOSITE_TEST,<Unused>,TEST_CLAUSE,"TEST ""@Value(_y2)"" >= ""@Value(_y1)""",_y2 >= _y1
    DEFAULT_VALUE = <UNFILTERED>
    _y2 >= _y1 -> ExpressionEvaluator_7
    <UNFILTERED> -> ExpressionEvaluator_4
Note: Calculate angle of the longest side
ExpressionEvaluator_7
    EXPRESSION = @atan2(@Value(_x1)-@Value(_x2),@Value(_y1)-@Value(_y2))*180.0/(22/7.0)
    VAL_ATTR = _angle
    -> ExpressionEvaluator_8
ExpressionEvaluator_4
    EXPRESSION = @atan2(@Value(_x2)-@Value(_x1),@Value(_y2)-@Value(_y1))*180.0/(22/7.0)
    VAL_ATTR = _angle
    -> ExpressionEvaluator_8
ExpressionEvaluator_8
    EXPRESSION = @Value(_angle) + 90.0
    VAL_ATTR = _angle
    -> TestFilter_5
TestFilter_5
    TEST_LIST = BOOL_OP,OR,COMPOSITE_TEST,<Unused>,TEST_CLAUSE,"TEST ""@Value(_angle)"" > ""180.0""",_angle > 180.0
    DEFAULT_VALUE = <UNFILTERED>
    _angle > 180.0 -> ExpressionEvaluator_10
    <UNFILTERED> -> Sorter_2
ExpressionEvaluator_10
    EXPRESSION = @Value(_angle) -180.0
    VAL_ATTR = _angle
    -> Sorter_2
Sorter_2
    SORT_PARM = _length NUMERIC DESCENDING
    SORTED -> FeatureMerger_3 [input 2]
FeatureMerger_3
    PROCESS_DUPS = No
    BUILD_INCOMPLETE = No
    MERGE_TYPE = Attributes Only
    REFERATTR = BUILDINGID
    REFEEATTR = BUILDINGID
    COMPLETE -> GeometryExtractor_2
GeometryExtractor_2
    KIND_LONG = FME Binary
    ATTR = _geometry
    -> CenterOfGravityReplacer
CenterOfGravityReplacer
    CENTEROFGRAVITY -> CoordinateExtractor_3
CoordinateExtractor_3
    X_ATTR = XCENTER
    Z_DEFAULT = -9999
    IND = 0
    Z_ATTR = _z
    Y_ATTR = YCENTER
    -> GeometryReplacer
GeometryReplacer
    KIND_LONG = FME Binary
    ATTR = _geometry
    -> AttributeCreator
Note: Calculate X and Y Center Point
AttributeCreator
    ATTR_LIST = BLDGHEIGHT,@Evaluate( abs(@Value(_y2) - @Value(_y1)) ),CALCROT,@Value(_angle)
    -> OUTPUT (output)
OUTPUT (output)

FME custom transformer gzAggregateLines
Clean geometries and Aggregate Floorplan lines into _Optimized features

INPUT (input)
    -> CoordinateCounter
CoordinateCounter
    CNT_ATTR = _coordcount
    -> LengthCalculator_2
LengthCalculator_2
    DIM = 2
    MULT = 1
    LEN_ATTR = _length
    -> TestFilter_6
TestFilter_6
    TEST_LIST:
      BOOL_OP,AND,COMPOSITE_TEST,<Unused>,TEST_CLAUSE,"TEST ""@Value(_coordcount)"" >= ""2""
      TEST ""@Value(_length)"" >= "".001""",2pts & length > .01
    DEFAULT_VALUE = <UNFILTERED>
    2pts & length > .01 -> SelfIntersectChecker
SelfIntersectChecker
    NotSelfIntersecting -> GeometryCoercer
    SelfIntersecting -> SelfIntersector
SelfIntersector
    SEG_ATTR = _segments
    SELF_INTERSECTED -> GeometryCoercer
GeometryCoercer
    KIND = fme_line
    COERCED -> Aggregator_2
Aggregator_2
    ACCUM_ATTRS_NAME = Yes
    SEP = ,
    ORDERED = No
    GROUP_BY = FACFLOOR
    CONTAIN_INDIVID_GEOMS = No
    AGGREGATE -> OUTPUT (output)
OUTPUT (output)
