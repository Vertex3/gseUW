FME workspace xgseSyncRoutingToPublication.fmw

Parameters:
- GEODATABASE_SDE_IN_CONNECTION_FILE_GEODATABASE_SDE = C:\Apps\Gizinta\gseUW\ETL\serverConfig\GIS Production.sde   # Connection File
- GEODATABASE_SDE_OUT_CONNECTION_FILE_GEODATABASE_SDE = C:\Apps\Gizinta\gseUW\ETL\serverConfig\GIS Publication.sde   # Connection File
- DestDataset_GEODATABASE_SDE = sde   # Destination Esri ArcSDE Geodatabase Dataset

Readers:
- GEODATABASE_SDE_2: GEODATABASE_SDE from $(DestDataset_GEODATABASE_SDE)

Writers:
- GEODATABASE_SDE_3: GEODATABASE_SDE to $(DestDataset_GEODATABASE_SDE)

DBO.RT_Waypoint (reader GEODATABASE_SDE_2)
    attributes: geodb_oid integer, OBJECTID integer, SITEID char(60), BUILDINGID char(60), FLOORCODE char(60), FLOORID char(60), ACTIVE smallint, ISPUBLIC smallint, NAME char(255), WAYPOINTTYPE char(20), SOURCEID char(30), SOURCEDWG char(60), LASTUPDATE date, LASTEDITOR char(30)
    -> DBO.RT_Waypoint (writer GEODATABASE_SDE_3)
DBO.RT_Waypoint (writer GEODATABASE_SDE_3)
    attributes: geodb_oid integer, OBJECTID integer, SITEID char(60), BUILDINGID char(60), FLOORCODE char(60), FLOORID char(60), ACTIVE smallint, ISPUBLIC smallint, NAME char(255), WAYPOINTTYPE char(20), SOURCEID char(30), SOURCEDWG char(60), LASTUPDATE date, LASTEDITOR char(30)
DBO.RT_Stop (reader GEODATABASE_SDE_2)
    attributes: geodb_oid integer, OBJECTID integer, SITEID char(60), BUILDINGID char(60), FLOORCODE char(60), FLOORID char(60), SPACEID1 char(50), SPACEID2 char(50), ADA smallint, FITNESS smallint, ACTIVE smallint, ISPUBLIC smallint, NAME char(255), WIDTH double, HEIGHT double, DELAY double, EMERGENCY char(255), SOURCEID char(30), SOURCEDWG char(60), LASTUPDATE date, LASTEDITOR char(30)
    -> DBO.RT_Stop (writer GEODATABASE_SDE_3)
DBO.RT_Stop (writer GEODATABASE_SDE_3)
    attributes: geodb_oid integer, OBJECTID integer, SITEID char(60), BUILDINGID char(60), FLOORCODE char(60), FLOORID char(60), SPACEID1 char(50), SPACEID2 char(50), ADA smallint, FITNESS smallint, ACTIVE smallint, ISPUBLIC smallint, NAME char(255), WIDTH double, HEIGHT double, DELAY double, EMERGENCY char(255), SOURCEID char(30), SOURCEDWG char(60), LASTUPDATE date, LASTEDITOR char(30)
DBO.RT_RoomPoint (reader GEODATABASE_SDE_2)
    attributes: geodb_oid integer, OBJECTID integer, SITEID char(60), BUILDINGID char(60), FLOORCODE char(60), FLOORID char(60), ROOMNUMBER char(26), SPACEID char(25), ADA smallint, FITNESS smallint, ACTIVE smallint, ISPUBLIC smallint, NAME char(255), EMERGENCY char(255), SOURCEID char(30), SOURCEDWG char(60), LASTUPDATE date, LASTEDITOR char(30)
    -> DBO.RT_RoomPoint (writer GEODATABASE_SDE_3)
DBO.RT_RoomPoint (writer GEODATABASE_SDE_3)
    attributes: geodb_oid integer, OBJECTID integer, SITEID char(60), BUILDINGID char(60), FLOORCODE char(60), FLOORID char(60), ROOMNUMBER char(26), SPACEID char(25), ADA smallint, FITNESS smallint, ACTIVE smallint, ISPUBLIC smallint, NAME char(255), EMERGENCY char(255), SOURCEID char(30), SOURCEDWG char(60), LASTUPDATE date, LASTEDITOR char(30)
DBO.RT_LineTransition (reader GEODATABASE_SDE_2)
    attributes: geodb_oid integer, OBJECTID integer, SITEID char(60), BUILDINGID char(60), FLOORCODE char(60), FLOORID char(60), SPACEID char(50), ADA smallint, EVAC char(255), FITNESS smallint, ACTIVE smallint, ISPUBLIC smallint, SURFACE char(255), SPEED double, NAME char(255), WIDTH double, HEIGHT double, ONEWAY char(255), EMERGENCY char(255), FROMFLOOR char(255), TOFLOOR char(255), ROUTECLASS smallint, SOURCEID char(30), SOURCEDWG char(60), LASTUPDATE date, LASTEDITOR char(30), SHAPE.STLength() double
    -> DBO.RT_LineTransition (writer GEODATABASE_SDE_3)
DBO.RT_LineTransition (writer GEODATABASE_SDE_3)
    attributes: geodb_oid integer, OBJECTID integer, SITEID char(60), BUILDINGID char(60), FLOORCODE char(60), FLOORID char(60), SPACEID char(50), ADA smallint, EVAC char(255), FITNESS smallint, ACTIVE smallint, ISPUBLIC smallint, SURFACE char(255), SPEED double, NAME char(255), WIDTH double, HEIGHT double, ONEWAY char(255), EMERGENCY char(255), FROMFLOOR char(255), TOFLOOR char(255), ROUTECLASS smallint, SOURCEID char(30), SOURCEDWG char(60), LASTUPDATE date, LASTEDITOR char(30), SHAPE.STLength() double
DBO.RT_LineRmConnector (reader GEODATABASE_SDE_2)
    attributes: geodb_oid integer, OBJECTID integer, SITEID char(60), BUILDINGID char(60), FLOORCODE char(60), FLOORID char(60), ROOMNUMBER char(26), SPACEID char(25), ADA smallint, FITNESS smallint, ACTIVE smallint, ISPUBLIC smallint, SURFACE char(255), SPEED double, WIDTH double, HEIGHT double, NAME char(255), ONEWAY char(255), EMERGENCY char(255), FROMFLOOR char(255), TOFLOOR char(255), ROUTECLASS smallint, SOURCEID char(30), SOURCEDWG char(60), LASTUPDATE date, LASTEDITOR char(30), SHAPE.STLength() double
    -> DBO.RT_LineRmConnector (writer GEODATABASE_SDE_3)
DBO.RT_LineRmConnector (writer GEODATABASE_SDE_3)
    attributes: geodb_oid integer, OBJECTID integer, SITEID char(60), BUILDINGID char(60), FLOORCODE char(60), FLOORID char(60), ROOMNUMBER char(26), SPACEID char(25), ADA smallint, FITNESS smallint, ACTIVE smallint, ISPUBLIC smallint, SURFACE char(255), SPEED double, WIDTH double, HEIGHT double, NAME char(255), ONEWAY char(255), EMERGENCY char(255), FROMFLOOR char(255), TOFLOOR char(255), ROUTECLASS smallint, SOURCEID char(30), SOURCEDWG char(60), LASTUPDATE date, LASTEDITOR char(30), SHAPE.STLength() double
DBO.RT_LineInterior (reader GEODATABASE_SDE_2)
    attributes: geodb_oid integer, OBJECTID integer, SITEID char(60), BUILDINGID char(60), FLOORCODE char(60), FLOORID char(60), SpaceID char(50), ADA smallint, EVAC char(255), FITNESS smallint, ACTIVE smallint, ISPUBLIC smallint, SURFACE char(255), SPEED double, NAME char(255), WIDTH double, HEIGHT double, ONEWAY char(255), EMERGENCY char(255), FROMFLOOR char(255), TOFLOOR char(255), ROUTECLASS smallint, SOURCEID char(30), SOURCEDWG char(60), LASTUPDATE date, LASTEDITOR char(30), SHAPE.STLength() double
    -> DBO.RT_LineInterior (writer GEODATABASE_SDE_3)
DBO.RT_LineInterior (writer GEODATABASE_SDE_3)
    attributes: geodb_oid integer, OBJECTID integer, SITEID char(60), BUILDINGID char(60), FLOORCODE char(60), FLOORID char(60), SpaceID char(50), ADA smallint, EVAC char(255), FITNESS smallint, ACTIVE smallint, ISPUBLIC smallint, SURFACE char(255), SPEED double, NAME char(255), WIDTH double, HEIGHT double, ONEWAY char(255), EMERGENCY char(255), FROMFLOOR char(255), TOFLOOR char(255), ROUTECLASS smallint, SOURCEID char(30), SOURCEDWG char(60), LASTUPDATE date, LASTEDITOR char(30), SHAPE.STLength() double
DBO.RT_DoorPoint (reader GEODATABASE_SDE_2)
    attributes: geodb_oid integer, OBJECTID integer, SITEID char(60), BUILDINGID char(60), FLOORCODE char(60), FLOORID char(60), DOOR char(20), DOORID char(33), SPACEID1 char(50), SPACEID2 char(50), ADA smallint, FITNESS smallint, ACTIVE smallint, ISPUBLIC smallint, WIDTH double, HEIGHT double, NAME char(255), EMERGENCY char(255), DELAY double, SUNTIMEWINDOWSTART date, SUNTIMEWINDOWEND date, MONTIMEWINDOWSTART date, MONTIMEWINDOWEND date, TUESTIMEWINDOWSTART date, TUESTIMEWINDOWEND date, WEDTIMEWINDOWSTART date, WEDTIMEWINDOWEND date, THURSTIMEWINDOWSTART date, THURSTIMEWINDOWEND date, FRITIMEWINDOWSTART date,
      FRITIMEWINDOWEND date, SATTIMEWINDOWSTART date, SATTIMEWINDOWEND date, SOURCEID char(30), SOURCEDWG char(60), LASTUPDATE date, LASTEDITOR char(30)
    -> DBO.RT_DoorPoint (writer GEODATABASE_SDE_3)
DBO.RT_DoorPoint (writer GEODATABASE_SDE_3)
    attributes: geodb_oid integer, OBJECTID integer, SITEID char(60), BUILDINGID char(60), FLOORCODE char(60), FLOORID char(60), DOOR char(20), DOORID char(33), SPACEID1 char(50), SPACEID2 char(50), ADA smallint, FITNESS smallint, ACTIVE smallint, ISPUBLIC smallint, WIDTH double, HEIGHT double, NAME char(255), EMERGENCY char(255), DELAY double, SUNTIMEWINDOWSTART date, SUNTIMEWINDOWEND date, MONTIMEWINDOWSTART date, MONTIMEWINDOWEND date, TUESTIMEWINDOWSTART date, TUESTIMEWINDOWEND date, WEDTIMEWINDOWSTART date, WEDTIMEWINDOWEND date, THURSTIMEWINDOWSTART date, THURSTIMEWINDOWEND date, FRITIMEWINDOWSTART date,
      FRITIMEWINDOWEND date, SATTIMEWINDOWSTART date, SATTIMEWINDOWEND date, SOURCEID char(30), SOURCEDWG char(60), LASTUPDATE date, LASTEDITOR char(30)
